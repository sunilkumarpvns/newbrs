NETVERTEX-PCRF-MIB DEFINITIONS ::= BEGIN

IMPORTS
       MODULE-IDENTITY, OBJECT-TYPE, OBJECT-IDENTITY,
       NOTIFICATION-TYPE,Counter32, Integer32, 
       Gauge32,TimeTicks				FROM SNMPv2-SMI
	   SnmpAdminString
            FROM SNMP-FRAMEWORK-MIB; -- [RFC3411]


       internet      OBJECT IDENTIFIER ::= { iso org(3) dod(6) 1 }

       directory     OBJECT IDENTIFIER ::= { internet 1 }

       mgmt          OBJECT IDENTIFIER ::= { internet 2 }

       experimental  OBJECT IDENTIFIER ::= { internet 3 }

       private       OBJECT IDENTIFIER ::= { internet 4 }

       enterprises   OBJECT IDENTIFIER ::= { private 1 }

	   elitecore   OBJECT IDENTIFIER ::= { enterprises 21067 }
            
	   netvertex   OBJECT IDENTIFIER ::= { elitecore 4 }

            
netvertexPCRF MODULE-IDENTITY
       LAST-UPDATED "9906110000Z"
       ORGANIZATION "EliteCore AAA Working Group."
       CONTACT-INFO
              " jatin zaveri
                Elitecore

		904, Silicon Tower, 
                Behind Pariseema Building, 
	        Off C.G.Road, Nr. Lal Bungalow, 
                Ahmedabad 380 006, INDIA.

                EMail: netvertex@elitecore.com"
       DESCRIPTION
             "The MIB module for entities implementing the netvertex-pcrf 
              server side."
       REVISION "1209270000Z"    --  27 Sep 2012
       DESCRIPTION "Initial version"
       ::= { netvertex 1 }


netvertexPCRFTraps OBJECT IDENTIFIER ::= { netvertexPCRF 1 }

nvGenericTrap NOTIFICATION-TYPE 
    STATUS  current
    DESCRIPTION
		"NetVertex Generic Notification"
	::= { netvertexPCRFTraps 1 }
		 
alertSeverity OBJECT-TYPE
	SYNTAX     SnmpAdminString
	MAX-ACCESS read-only
	STATUS  current
	DESCRIPTION
		"Notification signifies NetVertex Alert Severity."
	::= { netvertexPCRFTraps 2 }
		
alertOtherInfo OBJECT-TYPE
	SYNTAX     SnmpAdminString
	MAX-ACCESS read-only
	STATUS  current
	DESCRIPTION
		"Notification signifies NetVertex Alert additional information."
	::= { netvertexPCRFTraps 3 }

license OBJECT IDENTIFIER ::= { netvertexPCRFTraps 4 }

nvLicenseGeneric NOTIFICATION-TYPE
	STATUS  current
	DESCRIPTION
		"NetVertex License Generic Trap"
	::= { license 1 }

nvLicenseRenew NOTIFICATION-TYPE
	STATUS  current
	DESCRIPTION
		"Notification signifies NetVertex license renewal alerted"
	::= { license 2 }

nvLicenseExpired NOTIFICATION-TYPE
	STATUS  current
	DESCRIPTION
		"Notification signifies NetVertex license is expired"
	::= { license 3 }

nvLicenseExceed NOTIFICATION-TYPE
	STATUS  current
	DESCRIPTION
		"Notification signifies NetVertex license exceeded for some parameter"
	::= { license 4 }

nvLicenseRequestFailed NOTIFICATION-TYPE
    STATUS  current
    DESCRIPTION
        "Notification signifies NetVertex license requests are failing"
    ::= { license 5 }

server OBJECT IDENTIFIER ::= { netvertexPCRFTraps 5 }
-- server type of Traps

nvServerGeneric NOTIFICATION-TYPE 
	STATUS  current
	DESCRIPTION
		"NetVertex Server Generic Trap"
	::= { server 1 }

nvServerUp NOTIFICATION-TYPE
	STATUS  current
	DESCRIPTION
		"Notification signifies NetVertex Server is Up."
	::= { server 2 }
         
nvServerDown NOTIFICATION-TYPE
	STATUS  current
	DESCRIPTION
		"Notification signifies NetVertex Server is Down."
	::= { server 3 }

serverInstanceId NOTIFICATION-TYPE
	STATUS  current
	DESCRIPTION
		"Notification signifies the Identity of server."
	::= { server 4 }
		 
services OBJECT IDENTIFIER ::= { netvertexPCRFTraps 6 }

nvServiceGeneric NOTIFICATION-TYPE
	STATUS  current
	DESCRIPTION
		"NetVertex Service Generic Trap"
	::= { services 1 }

pcrf OBJECT IDENTIFIER ::= { services 2 }
-- PCRF Service Related Traps
nvPCRFServiceGeneric NOTIFICATION-TYPE
	STATUS  current
	DESCRIPTION
		"NetVertex PCRF Service Generic Trap"
	::= { pcrf 1 }
	
nvPCRFServiceStartUpFailed NOTIFICATION-TYPE
	STATUS  current
	DESCRIPTION
		"Notification signifies NetVertex PCRF Service Start Up Failed"
	::= { pcrf 2 }

nvSPRGeneric NOTIFICATION-TYPE
	STATUS  current
	DESCRIPTION
		"Notification signifies NetVertex Subscriber Profile Repository Generic Trap."
	::= { pcrf 3 }

nvSPRDown NOTIFICATION-TYPE
	STATUS  current
	DESCRIPTION
		"Notification signifies NetVertex Subscriber Profile Repository is down."
	::= { pcrf 4 }

nvSPRUp NOTIFICATION-TYPE
	STATUS  current
	DESCRIPTION
		"Notification signifies NetVertex Subscriber Profile Repository is up."
	::= { pcrf 5 }

nvQueryTimeout NOTIFICATION-TYPE
	STATUS  current
	DESCRIPTION
		"Notification signifies NetVertex Query Timeout."
	::= { pcrf 6 }

nvUnknownUser NOTIFICATION-TYPE
	STATUS  current
	DESCRIPTION
		"Notification signifies PCRF service received request from Unknown User."
	::= { pcrf 7 }

-- PCRF Service Related Traps finish

-- Notification Service Related Traps
notification OBJECT IDENTIFIER ::= { services 3 }

nvNotificationGeneric NOTIFICATION-TYPE
	STATUS  current
	DESCRIPTION
		"NetVertex Notification Generic Trap"
	::= { notification 1 }
	
nvNotificationServiceStartUpFailed NOTIFICATION-TYPE
	STATUS  current
	DESCRIPTION
		"Notification signifies NetVertex Notification Service Start Up Failed"
	::= { notification 2 }

nvNotificationBatchOver NOTIFICATION-TYPE
	STATUS  current
	DESCRIPTION 
		"Notification signifies NetVertex Notification Batch completed."
	::= { notification 3 }

nvEmailNotificationFailure NOTIFICATION-TYPE
	STATUS  current
	DESCRIPTION 
		"Notification signifies distinct NetVertex E-mail Notification Failure."
	::= { notification 4 }

nvSMSNotificationFailure NOTIFICATION-TYPE
	STATUS  current
	DESCRIPTION 
		"Notification signifies NetVertex SMS Notification Failure."
	::= { notification 5 }

-- Notification Service Related Traps finish


bod OBJECT IDENTIFIER ::= { services 4 }
-- BoD Service Related Traps
nvBoDServiceGeneric NOTIFICATION-TYPE
	STATUS  current
	DESCRIPTION
		"NetVertex BoD Service Generic Trap"
	::= { bod 1 }
	
nvBoDServiceStartUpFailed NOTIFICATION-TYPE
	STATUS  current
	DESCRIPTION
		"Notification signifies NetVertex BoD Service Start Up Failed"
	::= { bod 2 }

promotional OBJECT IDENTIFIER ::= { services 5 }
-- Promotional Service Related Traps
nvPromotionalServiceGeneric NOTIFICATION-TYPE
	STATUS  current
	DESCRIPTION
		"NetVertex Promotional Service Generic Trap"
	::= { promotional 1 }
	
nvPromotionalServiceStartUpFailed NOTIFICATION-TYPE
	STATUS  current
	DESCRIPTION
		"Notification signifies NetVertex Promotional Service Start Up Failed"
	::= { promotional 2 }

quotaProvision OBJECT IDENTIFIER ::= { services 6 }
-- QuotaProvision Service Related Traps
nvQuotaProvisionServiceGeneric NOTIFICATION-TYPE
	STATUS  current
	DESCRIPTION
		"NetVertex QuotaProvision Service Generic Trap"
	::= { quotaProvision 1 }
	
nvQuotaProvisionServiceStartUpFailed NOTIFICATION-TYPE
	STATUS  current
	DESCRIPTION
		"Notification signifies NetVertex QuotaProvision Service Start Up Failed"
	::= { quotaProvision 2 }

gateways OBJECT IDENTIFIER ::= { netvertexPCRFTraps 7 }
-- Gateways
nvGatewayGeneric NOTIFICATION-TYPE
	STATUS  current
	DESCRIPTION
		"NetVertex Gateway Generic Trap"
	::= { gateways 1 }

radius OBJECT IDENTIFIER ::= { gateways 2 }
nvRadiusGwGeneric NOTIFICATION-TYPE
    STATUS  current
    DESCRIPTION
        "NetVertex RADIUS Gateway Generic Trap"
	::= { radius 1 }

nvRadiusGwAlive NOTIFICATION-TYPE
    STATUS  current
    DESCRIPTION
		"Notification signifies NetVertex RADIUS Gateway is Alive."
	::= { radius 2 }

nvRadiusGwDead NOTIFICATION-TYPE
	STATUS  current
    DESCRIPTION
		"Notification signifies NetVertex RADIUS Gateway is Dead."
	::= { radius 3 }

diameter OBJECT IDENTIFIER ::= { gateways 3 }

nvDiameterGwGeneric NOTIFICATION-TYPE
	STATUS  current
	DESCRIPTION
		"Notification signifies NetVertex DIAMETER Gateway Generic Trap"
	::= { diameter 1 }

nvDiameterStackGeneric NOTIFICATION-TYPE
    STATUS  current
    DESCRIPTION
        "Notification signifies Diameter Stack Generic Trap."
	::= { diameter 2 }
	
nvDiameterStackUp NOTIFICATION-TYPE
    STATUS  current
    DESCRIPTION
        "Notification signifies NetVertex Diameter Stack is Up."
	::= { diameter 3 }

nvDiameterStackDown NOTIFICATION-TYPE
    STATUS  current
    DESCRIPTION
		"Notification signifies NetVertex Diameter Stack is Down."
	::= { diameter 4 }
	
nvDiameterPeerGeneric NOTIFICATION-TYPE
    STATUS  current
    DESCRIPTION
        "Notification signifies Diameter Peer Generic Trap."
	::= { diameter 5 }

nvDiameterPeerUp NOTIFICATION-TYPE
    STATUS  current
    DESCRIPTION
        "Notification signifies NetVertex Diameter Peer is Up."
	::= { diameter 6 }

nvDiameterPeerDown NOTIFICATION-TYPE
    STATUS  current
    DESCRIPTION
        "Notification signifies NetVertex Diameter Peer is Down."
	::= { diameter 7 }
	
nvDiameterHighResponseTime NOTIFICATION-TYPE
    STATUS  current
    DESCRIPTION
        "Notification signifies total processing time for received request from peer."
	::= { diameter 8 }

nvDiameterPeerConnectionRejected NOTIFICATION-TYPE
    STATUS  current
    DESCRIPTION
        "Notification signifies Diameter Peer connection rejected."
	::= { diameter 9 }	

nvDiameterPeerHighResponseTime NOTIFICATION-TYPE
    STATUS  current
    DESCRIPTION
        "Notification signifies response time for request sent from diameter stack to peer."
	::= { diameter 10 }	
	
policies OBJECT IDENTIFIER ::= { netvertexPCRFTraps 8 }
-- server type of Traps

nvPolicyGeneric NOTIFICATION-TYPE 
	STATUS  current
	DESCRIPTION
		"NetVertex Server Policy Generic Trap"
	::= { policies 1 }

nvSessionAuthRuleInitFails NOTIFICATION-TYPE
	STATUS  current
	DESCRIPTION
		"Notification signifies Session AuthRule Initialization Failed"
	::= { policies 2 }
         
nvServiceAuthRuleInitFails NOTIFICATION-TYPE
	STATUS  current
	DESCRIPTION
		"Notification signifies Service AuthRule Initialization Failed"
	::= { policies 3 }
	
nvPccRuleInitFails NOTIFICATION-TYPE
	STATUS  current
	DESCRIPTION
		"Notification signifies PCC Rule Initialization Failed"
	::= { policies 4 }

nvServicePolicyInitFails NOTIFICATION-TYPE
	STATUS  current
	DESCRIPTION
		"Notification signifies Service Policy Initialization Failed"
	::= { policies 5 }
	
database OBJECT IDENTIFIER ::= { netvertexPCRFTraps 9 }

nvDatabaseGeneric NOTIFICATION-TYPE
	STATUS  current
	DESCRIPTION
		"Database Generic Trap"
	::= { database 1 }

nvNoConnection NOTIFICATION-TYPE
	STATUS  current
	DESCRIPTION
		"Notification signifies no free Database connection available"
	::= { database 2 }	
	
nvHighQueryResponseTime NOTIFICATION-TYPE
	STATUS  current
	DESCRIPTION
		"Notification signifies database query execution time is high"
	::= { database 3 }
	
nvDataSourceUp NOTIFICATION-TYPE 
	STATUS current 
	DESCRIPTION 
	"Notification signifies database datasource is Up" 
	::= { database 4 } 
	
nvDataSourceDown NOTIFICATION-TYPE 
	STATUS current 
	DESCRIPTION 
	"Notification signifies database datasource is Down" 
	::= { database 5 }

netvertexPCRFStatistics OBJECT IDENTIFIER ::= { netvertexPCRF 2 }

serviceStatistics OBJECT IDENTIFIER ::= { netvertexPCRFStatistics 1 }

pcrfStatistics OBJECT IDENTIFIER ::= { serviceStatistics 1 }

pcrfServiceUpTime OBJECT-TYPE
	SYNTAX      TimeTicks
	MAX-ACCESS  read-only
	STATUS      current
	DESCRIPTION
		 "This value will be the time elapsed (in hundredths of a second)
		 since the PCRF service started."
       ::= { pcrfStatistics 1 }

pcrfStatisticsResetTime OBJECT-TYPE
	SYNTAX      TimeTicks
	MAX-ACCESS  read-only
	STATUS      current
	DESCRIPTION
		 "This value will be the time elapsed (in hundredths of a second) 
		 since the PCRF service  statistics was `reset.'"
       ::= { pcrfStatistics 2 }

pcrfStatisticsReset OBJECT-TYPE
	SYNTAX INTEGER { other(1),
                     reset(2),
                     initializing(3),
                     running(4)}
	MAX-ACCESS  read-write
	STATUS      current
	DESCRIPTION
		 "When set to reset(2), PCRF service statistics is reinitialized.
          When read, one of the following values will be returned:
                   other(1) - service in some unknown state;
                   initializing(3) - service (einitializing;
                   running(4) - service currently running."
   ::= { pcrfStatistics 3 }

totalRequests OBJECT-TYPE
    SYNTAX Counter32
    MAX-ACCESS read-only
    STATUS current
    DESCRIPTION
         "The total number of PCRF requests received by PCRF service."
    ::= { pcrfStatistics 4 }

totalResponses OBJECT-TYPE
    SYNTAX Counter32
    MAX-ACCESS read-only
    STATUS current
    DESCRIPTION
         "The total number of PCRF responses given by PCRF service."
    ::= { pcrfStatistics 5 }

totalRequestDropped OBJECT-TYPE
    SYNTAX Counter32
    MAX-ACCESS read-only
    STATUS current
    DESCRIPTION
         "The total number of PCRF requests dropped by PCRF service."
    ::= { pcrfStatistics 6 }
	
totalSuccessResponses OBJECT-TYPE
    SYNTAX Counter32
    MAX-ACCESS read-only
    STATUS current
    DESCRIPTION
         "The total number of PCRF success responses given by PCRF service."
    ::= { pcrfStatistics 7 }

totalRejectResponses OBJECT-TYPE
    SYNTAX Counter32
    MAX-ACCESS read-only
    STATUS current
    DESCRIPTION
         "The total number of PCRF rejhect responses given by PCRF service."
    ::= { pcrfStatistics 8 }
	
avgRequestProcessingTime OBJECT-TYPE
    SYNTAX Counter32
    MAX-ACCESS read-only
    STATUS current
    DESCRIPTION
         "The average PCRF request prcessing time for last one minute."
    ::= { pcrfStatistics 9 }

avgTPS OBJECT-TYPE
    SYNTAX Counter32
    MAX-ACCESS read-only
    STATUS current
    DESCRIPTION
         "The average TPS in PCRF service for last one minute."
    ::= { pcrfStatistics 10 }
	
notificationStatistics OBJECT IDENTIFIER ::= { serviceStatistics 2 }

notificationServiceUpTime OBJECT-TYPE
	SYNTAX      TimeTicks
	MAX-ACCESS  read-only
	STATUS      current
	DESCRIPTION
		 "This value will be the time elapsed (in hundredths of a second)
		 since the Notification service started."
       ::= { notificationStatistics 1 }

notificationStatisticsResetTime OBJECT-TYPE
	SYNTAX      TimeTicks
	MAX-ACCESS  read-only
	STATUS      current
	DESCRIPTION
		 "This value will be the time elapsed (in hundredths of a second) 
		 since the Notification service  statistics was `reset.'"
       ::= { notificationStatistics 2 }

notificationStatisticsReset OBJECT-TYPE
	SYNTAX INTEGER { other(1),
                     reset(2),
                     initializing(3),
                     running(4)}
	MAX-ACCESS  read-write
	STATUS      current
	DESCRIPTION
		 "When read, one of the following values will be returned:
              other(1) - service in some unknown state;
              initializing(3) - service (einitializing;
              running(4) - service currently running.
		  When set to reset(2),  Notification service statistics is reinitialized."
   ::= { notificationStatistics 3 }

   
totalNotificationProcessed OBJECT-TYPE
    SYNTAX Counter32
    MAX-ACCESS read-only
    STATUS current
    DESCRIPTION
         "The total number of notification processed by notification service."
    ::= { notificationStatistics 4 }
	
totalEmailProcessed OBJECT-TYPE
    SYNTAX Counter32
    MAX-ACCESS read-only
    STATUS current
    DESCRIPTION
         "The total number of Email notification processed by notification service."
    ::= { notificationStatistics 5 }
	
totalEmailSuccess OBJECT-TYPE
    SYNTAX Counter32
    MAX-ACCESS read-only
    STATUS current
    DESCRIPTION
         "The total number of Email notification successfully sent by notification service."
    ::= { notificationStatistics 6 }

totalEmailFailures OBJECT-TYPE
    SYNTAX Counter32
    MAX-ACCESS read-only
    STATUS current
    DESCRIPTION
         "The total number of Email notification sending failed by notification service."
    ::= { notificationStatistics 7 }

totalSMSProcessed OBJECT-TYPE
    SYNTAX Counter32
    MAX-ACCESS read-only
    STATUS current
    DESCRIPTION
         "The total number of SMS notification processed by notification service."
    ::= { notificationStatistics 8 }

totalSMSSuccess OBJECT-TYPE
    SYNTAX Counter32
    MAX-ACCESS read-only
    STATUS current
    DESCRIPTION
         "The total number of SMS notification successfully sent by notification service."
    ::= { notificationStatistics 9 }

totalSMSFailures OBJECT-TYPE
    SYNTAX Counter32
    MAX-ACCESS read-only
    STATUS current
    DESCRIPTION
         "The total number of SMS notification sending failed by notification service."
    ::= { notificationStatistics 10 }
	
	
-- Current Day Stats

totalNotificationProcessedToday OBJECT-TYPE
    SYNTAX Counter32
    MAX-ACCESS read-only
    STATUS current
    DESCRIPTION
         "The total number of notification processed today by notification service."
    ::= { notificationStatistics 21 }
	
totalEmailProcessedToday OBJECT-TYPE
    SYNTAX Counter32
    MAX-ACCESS read-only
    STATUS current
    DESCRIPTION
         "The total number of Email notification processed today by notification service."
    ::= { notificationStatistics 22 }
	
totalEmailSuccessToday OBJECT-TYPE
    SYNTAX Counter32
    MAX-ACCESS read-only
    STATUS current
    DESCRIPTION
         "The total number of Email notification successfully sent today by notification service."
    ::= { notificationStatistics 23 }

totalEmailFailuresToday OBJECT-TYPE
    SYNTAX Counter32
    MAX-ACCESS read-only
    STATUS current
    DESCRIPTION
         "The total number of Email notification sending failed today by notification service."
    ::= { notificationStatistics 24 }

totalSMSProcessedToday OBJECT-TYPE
    SYNTAX Counter32
    MAX-ACCESS read-only
    STATUS current
    DESCRIPTION
         "The total number of SMS notification processed today by notification service."
    ::= { notificationStatistics 25 }

totalSMSSuccessToday OBJECT-TYPE
    SYNTAX Counter32
    MAX-ACCESS read-only
    STATUS current
    DESCRIPTION
         "The total number of SMS notification successfully sent today by notification service."
    ::= { notificationStatistics 26 }

totalSMSFailuresToday OBJECT-TYPE
    SYNTAX Counter32
    MAX-ACCESS read-only
    STATUS current
    DESCRIPTION
         "The total number of SMS notification sending failed today by notification service."
    ::= { notificationStatistics 27 }

	
-- Yesterday Day Stats

totalNotificationProcessedYesterday OBJECT-TYPE
    SYNTAX Counter32
    MAX-ACCESS read-only
    STATUS current
    DESCRIPTION
         "The total number of notification processed yesterday by notification service."
    ::= { notificationStatistics 41 }
	
totalEmailProcessedYesterday OBJECT-TYPE
    SYNTAX Counter32
    MAX-ACCESS read-only
    STATUS current
    DESCRIPTION
         "The total number of Email notification processed yesterday by notification service."
    ::= { notificationStatistics 42 }
	
totalEmailSuccessYesterday OBJECT-TYPE
    SYNTAX Counter32
    MAX-ACCESS read-only
    STATUS current
    DESCRIPTION
         "The total number of Email notification successfully sent yesterday by notification service."
    ::= { notificationStatistics 43 }

totalEmailFailuresYesterday OBJECT-TYPE
    SYNTAX Counter32
    MAX-ACCESS read-only
    STATUS current
    DESCRIPTION
         "The total number of Email notification sending failed yesterday by notification service."
    ::= { notificationStatistics 44 }

totalSMSProcessedYesterday OBJECT-TYPE
    SYNTAX Counter32
    MAX-ACCESS read-only
    STATUS current
    DESCRIPTION
         "The total number of SMS notification processed yesterday by notification service."
    ::= { notificationStatistics 45 }

totalSMSSuccessYesterday OBJECT-TYPE
    SYNTAX Counter32
    MAX-ACCESS read-only
    STATUS current
    DESCRIPTION
         "The total number of SMS notification successfully sent yesterday by notification service."
    ::= { notificationStatistics 46 }

totalSMSFailuresYesterday OBJECT-TYPE
    SYNTAX Counter32
    MAX-ACCESS read-only
    STATUS current
    DESCRIPTION
         "The total number of SMS notification sending failed yesterday by notification service."
    ::= { notificationStatistics 47 }

usageStatistics OBJECT IDENTIFIER ::= { serviceStatistics 3 }

totalUsageReportedInLastHour OBJECT-TYPE
    SYNTAX Counter64
    MAX-ACCESS read-only
    STATUS current
    DESCRIPTION
         "The total usage reported in last hour of the day."
    ::= { usageStatistics 1 }
	
totalUsageReportedInCurrentDay OBJECT-TYPE
    SYNTAX Counter64
    MAX-ACCESS read-only
    STATUS current
    DESCRIPTION
         "The total usage reported in current day."
    ::= { usageStatistics 2 }

totalUsageReportedInYesterday OBJECT-TYPE
    SYNTAX Counter64
    MAX-ACCESS read-only
    STATUS current
    DESCRIPTION
         "The total usage reported in yesterday."
    ::= { usageStatistics 3 }
	
totalUsageReportedInLast24Hours OBJECT-TYPE
    SYNTAX Counter64
    MAX-ACCESS read-only
    STATUS current
    DESCRIPTION
         "The total usage reported in last 24 hours."
    ::= { usageStatistics 4 }
    
usageStatisticsResetTime OBJECT-TYPE
    SYNTAX      TimeTicks
    MAX-ACCESS  read-only
    STATUS      current
    DESCRIPTION
        "This value will be the time elapsed (in hundredths of a second) 
         since the Usage statistics was `reset.'"
       ::= { usageStatistics 5 }

usageStatisticsReset OBJECT-TYPE
    SYNTAX INTEGER { yes(1),
                     no(2)}
    MAX-ACCESS  read-write
    STATUS      current
    DESCRIPTION
        "When set to no(2),  Usage statistics will not reinitialize.
         yes(1),  Usage statistics will reinitialize."
   ::= { usageStatistics 6 }
    

sessionCacheStatistics OBJECT IDENTIFIER ::= { serviceStatistics 4 }

totalCacheCount OBJECT-TYPE
	SYNTAX      Counter32
	MAX-ACCESS  read-only
	STATUS      current
	DESCRIPTION
		 "This value will be the total cached sessions."
       ::= { sessionCacheStatistics 1 }

totalHitCount OBJECT-TYPE
	SYNTAX      Counter32
	MAX-ACCESS  read-only
	STATUS      current
	DESCRIPTION
		 "This value will be total success fetch from cache."
       ::= { sessionCacheStatistics 2 }

totalMissedCount OBJECT-TYPE
	SYNTAX      Counter32
	MAX-ACCESS  read-only
	STATUS      current
	DESCRIPTION
		 "This value will be missed fetch from cache."
       ::= { sessionCacheStatistics 3 }

totalRequestCount OBJECT-TYPE
	SYNTAX      Counter32
	MAX-ACCESS  read-only
	STATUS      current
	DESCRIPTION
		 "This value will be total request for cache."
       ::= { sessionCacheStatistics 4 }

totalLoadCount OBJECT-TYPE
	SYNTAX      Counter32
	MAX-ACCESS  read-only
	STATUS      current
	DESCRIPTION
		 "This value will be total count for loading cache."
       ::= { sessionCacheStatistics 5 }

totalAverageLoadPanelty OBJECT-TYPE
	SYNTAX      Counter32
	MAX-ACCESS  read-only
	STATUS      current
	DESCRIPTION
		 "This value will be average load time of cache in milliseconds."
       ::= { sessionCacheStatistics 6 }

totalEvictionCount OBJECT-TYPE
	SYNTAX      Counter32
	MAX-ACCESS  read-only
	STATUS      current
	DESCRIPTION
		 "This value will be count of eviction of cache."
       ::= { sessionCacheStatistics 7 }

-- GLOBAL WEBSERVICE BEGIN 

netvertexWebServiceStatistics OBJECT IDENTIFIER ::= { netvertexPCRF 3 }

webServiceTotalRequests OBJECT-TYPE
    SYNTAX Counter32
    MAX-ACCESS read-only
    STATUS current
    DESCRIPTION
         "Total number of Web-Service requests received by Policy Designer."
    ::= { netvertexWebServiceStatistics 1 }

webServiceTotalResponses OBJECT-TYPE
    SYNTAX Counter32
    MAX-ACCESS read-only
    STATUS current
    DESCRIPTION
         "Total number of Web-Service responses given by Policy Designer."
    ::= { netvertexWebServiceStatistics 2 }

webServiceLastMinuteTotalRequests OBJECT-TYPE
    SYNTAX Counter32
    MAX-ACCESS read-only
    STATUS current
    DESCRIPTION
         "Total number of Web-Service requests received in Last Minute by Policy Designer."
    ::= { netvertexWebServiceStatistics 3 }

webServiceAvgTPS OBJECT-TYPE
    SYNTAX Counter32
    MAX-ACCESS read-only
    STATUS current
    DESCRIPTION
         "The average TPS in Web-Service for last one minute."
    ::= { netvertexWebServiceStatistics 4 }
	
webServiceUpTime OBJECT-TYPE
	SYNTAX      TimeTicks
	MAX-ACCESS  read-only
	STATUS      current
	DESCRIPTION
		 "This value will be the time elapsed (in hundredths of a second)
		 since the Web-Service started."
       ::= { netvertexWebServiceStatistics 5 }

webServiceLastResetTime OBJECT-TYPE
	SYNTAX      TimeTicks
	MAX-ACCESS  read-only
	STATUS      current
	DESCRIPTION
		 "This value will be the time, when the web-service statistics were reset last time"
       ::= { netvertexWebServiceStatistics 6 }

webServiceStatisticsReset OBJECT-TYPE
	SYNTAX INTEGER { other(1),
                     reset(2),
                     initializing(3),
                     running(4)}
	MAX-ACCESS  read-write
	STATUS      current
	DESCRIPTION
		 "When set to reset(2), Web-Service statistics is reinitialized.
          When read, one of the following values will be returned:
                   other(1) - Web-Service in some unknown state;
                   initializing(3) - Web-Service Reinitializing;
                   running(4) - Web-Service currently running."
   ::= { netvertexWebServiceStatistics 7 }
   
		
webServiceResultCodeWiseStatisticsTable OBJECT-TYPE
       SYNTAX     SEQUENCE OF WebServiceResultCodeWiseSeq
       MAX-ACCESS not-accessible
       STATUS     current
       DESCRIPTION
             "The (conceptual) table listing the Web-Service ResultCodes statistics."
       ::= { netvertexWebServiceStatistics 8 }
       
WebServiceResultCodeWiseSeq ::= SEQUENCE {             
       webServiceResultCode	Counter32,
       webServiceResultCodeName	SnmpAdminString,
       webServiceResultCodeCounters	Counter32       
 }       
	
webServiceResultCodeWiseEntry OBJECT-TYPE
       SYNTAX     WebServiceResultCodeWiseSeq
       MAX-ACCESS not-accessible
       STATUS     current
       DESCRIPTION
             "An entry (conceptual row) representing a Web-Service ResultCode specific statistics."

       INDEX      { webServiceResultCode }
       ::= { webServiceResultCodeWiseStatisticsTable 1 }   
       
webServiceResultCode OBJECT-TYPE
       SYNTAX     Integer32 (1..2147483647)
       MAX-ACCESS not-accessible
       STATUS     current
       DESCRIPTION
             "Web-Service ResultCode."
       ::= { webServiceResultCodeWiseEntry 1 }       
   
webServiceResultCodeName OBJECT-TYPE
    SYNTAX SnmpAdminString
    MAX-ACCESS read-only
    STATUS current
    DESCRIPTION
         "Web-Service ResultCode Name."
    ::= { webServiceResultCodeWiseEntry 2 }

webServiceResultCodeCounters OBJECT-TYPE
    SYNTAX Counter32
    MAX-ACCESS read-only
    STATUS current
    DESCRIPTION
         "Web-Service ResultCode Counter."
    ::= { webServiceResultCodeWiseEntry 3 }

-- END OF GLOBAL-WS


-- SubscriptionWS BEGIN
	
subscriptionWSStatistics OBJECT IDENTIFIER ::= { netvertexWebServiceStatistics 9 }

subscriptionWSTotalRequests OBJECT-TYPE
    SYNTAX Counter32
    MAX-ACCESS read-only
    STATUS current
    DESCRIPTION
         "Total number of SubscriptionWS requests received by Policy Designer."
    ::= { subscriptionWSStatistics 1 }

subscriptionWSTotalResponses OBJECT-TYPE
    SYNTAX Counter32
    MAX-ACCESS read-only
    STATUS current
    DESCRIPTION
         "Total number of SubscriptionWS responses given by Policy Designer."
    ::= { subscriptionWSStatistics 2 }

subscriptionWSLastMinuteTotalRequests OBJECT-TYPE
    SYNTAX Counter32
    MAX-ACCESS read-only
    STATUS current
    DESCRIPTION
         "Total number of SubscriptionWS requests received in Last Minute by Policy Designer."
    ::= { subscriptionWSStatistics 3 }

subscriptionWSAvgTPS OBJECT-TYPE
    SYNTAX Counter32
    MAX-ACCESS read-only
    STATUS current
    DESCRIPTION
         "The average TPS in SubscriptionWS for last one minute."
    ::= { subscriptionWSStatistics 4 }
		
subscriptionWSMethodWiseStatisticsTable OBJECT-TYPE
       SYNTAX     SEQUENCE OF SubscriptionWSMethodWiseSeq
       MAX-ACCESS not-accessible
       STATUS     current
       DESCRIPTION
             "The (conceptual) table listing the SubscriptionWS method wise statistics."
       ::= { subscriptionWSStatistics 5 }
       
SubscriptionWSMethodWiseSeq ::= SEQUENCE {
       subscriptionWSMethodIndex   				Integer32,
       subscriptionWSMethodName     			SnmpAdminString,
       subscriptionWSMethodTotalRequests          	Counter32,
       subscriptionWSMethodTotalResponses         	Counter32,
       subscriptionWSMethodLastMinuteTotalRequests	Counter32,
       subscriptionWSMethodAvgTPS                 	Counter32
 }       
	
subscriptionWSMethodWiseEntry OBJECT-TYPE
       SYNTAX     SubscriptionWSMethodWiseSeq
       MAX-ACCESS not-accessible
       STATUS     current
       DESCRIPTION
             "An entry (conceptual row) representing a SubscriptionWS
              method specific statistics."

       INDEX      { subscriptionWSMethodIndex }
       ::= { subscriptionWSMethodWiseStatisticsTable 1 }
       
subscriptionWSMethodIndex OBJECT-TYPE
       SYNTAX     Integer32 (1..2147483647)
       MAX-ACCESS not-accessible
       STATUS     current
       DESCRIPTION
             "SubscriptionWS method's Index"
       ::= { subscriptionWSMethodWiseEntry 1 }
   
subscriptionWSMethodName OBJECT-TYPE
       SYNTAX     SnmpAdminString
       MAX-ACCESS read-only
       STATUS     current
       DESCRIPTION
             "SubscriptionWS method's Name"
       ::= { subscriptionWSMethodWiseEntry 2 }
       
subscriptionWSMethodTotalRequests OBJECT-TYPE
    SYNTAX Counter32
    MAX-ACCESS read-only
    STATUS current
    DESCRIPTION
         "Total number of SubscriptionWS method wise Requests received by particular method in Policy Designer."
    ::= { subscriptionWSMethodWiseEntry 3 }

subscriptionWSMethodTotalResponses OBJECT-TYPE
    SYNTAX Counter32
    MAX-ACCESS read-only
    STATUS current
    DESCRIPTION
         "Total number of SubscriptionWS method wise Responses given by particular method  in Policy Designer."
    ::= { subscriptionWSMethodWiseEntry 4 }

subscriptionWSMethodLastMinuteTotalRequests OBJECT-TYPE
    SYNTAX Counter32
    MAX-ACCESS read-only
    STATUS current
    DESCRIPTION
         "Total number of SubscriptionWS method wise Requests received in Last Minute by Policy Designer."
    ::= { subscriptionWSMethodWiseEntry 5 }

subscriptionWSMethodAvgTPS OBJECT-TYPE
    SYNTAX Counter32
    MAX-ACCESS read-only
    STATUS current
    DESCRIPTION
         "Method wise average TPS in SubscriptionWS for last one Minute"
    ::= { subscriptionWSMethodWiseEntry 6 }
       
-- SUBSCRIPTION-WS RESULT CODE STATISTICS BEGIN --
       
subscriptionWSResultCodeWiseStatisticsTable OBJECT-TYPE
       SYNTAX     SEQUENCE OF SubscriptionWSResultCodeWiseSeq
       MAX-ACCESS not-accessible
       STATUS     current
       DESCRIPTION
             "The (conceptual) table listing the SubscriptionWS ResultCodes statistics."
       ::= { subscriptionWSStatistics 6 }
       
SubscriptionWSResultCodeWiseSeq ::= SEQUENCE {             
       subscriptionWSResultCode  			Counter32,
       subscriptionWSResultCodeName  		SnmpAdminString,
       subscriptionWSResultCodeCounters  	Counter32       
}       
	
subscriptionWSResultCodeWiseEntry OBJECT-TYPE
       SYNTAX     SubscriptionWSResultCodeWiseSeq
       MAX-ACCESS not-accessible
       STATUS     current
       DESCRIPTION
             "An entry (conceptual row) representing a subscriptionWS ResultCode specific statistics."

       INDEX      { subscriptionWSResultCode }
       ::= { subscriptionWSResultCodeWiseStatisticsTable 1 }   
       
subscriptionWSResultCode OBJECT-TYPE
       SYNTAX     Integer32 (1..2147483647)
       MAX-ACCESS not-accessible
       STATUS     current
       DESCRIPTION
             "Web-Service ResultCode"
       ::= { subscriptionWSResultCodeWiseEntry 1 }       
   
subscriptionWSResultCodeName OBJECT-TYPE
    SYNTAX SnmpAdminString
    MAX-ACCESS read-only
    STATUS current
    DESCRIPTION
         "subscriptionWS ResultCode Name."
    ::= { subscriptionWSResultCodeWiseEntry 2 }

subscriptionWSResultCodeCounters OBJECT-TYPE
    SYNTAX Counter32
    MAX-ACCESS read-only
    STATUS current
    DESCRIPTION
         "SubscriptionWS ResultCode statistics."
    ::= { subscriptionWSResultCodeWiseEntry 3 }
    
-- SUBSCRIPTION-WS RESULT CODE COUNTERS END --
   
-- SUBSCRIPTION-WS METHOD WISE RESULT CODE BEGIN --

	-- SUBSCRIPTION-WS METHOD1 wsListAddOnPackages BEGIN --
	
	subscriptionWSListAddOnPackagesTable OBJECT-TYPE
	       SYNTAX     SEQUENCE OF ListAddOnPackagesSeq
	       MAX-ACCESS not-accessible
	       STATUS     current
	       DESCRIPTION
	             "The (conceptual) table listing the SubscriptionWS Method wise ResultCode statistics."
	       ::= { subscriptionWSStatistics 7 }
	       
	ListAddOnPackagesSeq ::= SEQUENCE {		                  
	       listAddOnPackagesResultCode  			Counter32,
	       listAddOnPackagesResultCodeName  		SnmpAdminString,
	       listAddOnPackagesResultCodeCounters  	Counter32       
	}       
		
	subscriptionWSListAddOnPackagesEntry OBJECT-TYPE
	       SYNTAX     ListAddOnPackagesSeq
	       MAX-ACCESS not-accessible
	       STATUS     current
	       DESCRIPTION
	             "An entry (conceptual row) representing a subscriptionWS method wsListAddOnPackages ResultCode specific counters."
	
	       INDEX      { listAddOnPackagesResultCode }
	       ::= { subscriptionWSListAddOnPackagesTable 1 }   
	       
	listAddOnPackagesResultCode OBJECT-TYPE
	       SYNTAX     Integer32 (1..2147483647)
	       MAX-ACCESS not-accessible
	       STATUS     current
	       DESCRIPTION
	             "SubscriptionWS method wslistAddOnPackages ResultCode"
	       ::= { subscriptionWSListAddOnPackagesEntry 1 }       
	   
	listAddOnPackagesResultCodeName OBJECT-TYPE
	    SYNTAX SnmpAdminString
	    MAX-ACCESS read-only
	    STATUS current
	    DESCRIPTION
	         "subscriptionWS listAddOnPackages ResultCode Name."
	    ::= { subscriptionWSListAddOnPackagesEntry 2 }
	
	listAddOnPackagesResultCodeCounters OBJECT-TYPE
	    SYNTAX Counter32
	    MAX-ACCESS read-only
	    STATUS current
	    DESCRIPTION
	         "SubscriptionWS method wsListAddOnPackages ResultCode Specific counters."
	    ::= { subscriptionWSListAddOnPackagesEntry 3 }
	    
	-- SUBSCRIPTION-WS METHOD1 wsListAddOnPackages END --        
	
	-- SUBSCRIPTION-WS METHOD2 wsListPackages BEGIN --
	
	subscriptionWSListPackagesTable OBJECT-TYPE
	       SYNTAX     SEQUENCE OF ListPackagesSeq
	       MAX-ACCESS not-accessible
	       STATUS     current
	       DESCRIPTION
	             "The (conceptual) table listing the SubscriptionWS Method wsListPackages ResultCode statistics."
	       ::= { subscriptionWSStatistics 8 }
	       
	ListPackagesSeq ::= SEQUENCE {		                  
	       listPackagesResultCode  			Counter32,
	       listPackagesResultCodeName  		SnmpAdminString,
	       listPackagesResultCodeCounters  	Counter32       
	}       
		
	subscriptionWSListPackagesEntry OBJECT-TYPE
	       SYNTAX     ListPackagesSeq
	       MAX-ACCESS not-accessible
	       STATUS     current
	       DESCRIPTION
	             "An entry (conceptual row) representing a subscriptionWS method wsListPackages ResultCode specific counters."
	
	       INDEX      { listPackagesResultCode }
	       ::= { subscriptionWSListPackagesTable 1 }   
	       
	listPackagesResultCode OBJECT-TYPE
	       SYNTAX     Integer32 (1..2147483647)
	       MAX-ACCESS not-accessible
	       STATUS     current
	       DESCRIPTION
	             "SubscriptionWS method wsListPackages ResultCode"
	       ::= { subscriptionWSListPackagesEntry 1 }       
	   
	listPackagesResultCodeName OBJECT-TYPE
	    SYNTAX SnmpAdminString
	    MAX-ACCESS read-only
	    STATUS current
	    DESCRIPTION
	         "subscriptionWS wsListPackages ResultCode Name."
	    ::= { subscriptionWSListPackagesEntry 2 }
	
	listPackagesResultCodeCounters OBJECT-TYPE
	    SYNTAX Counter32
	    MAX-ACCESS read-only
	    STATUS current
	    DESCRIPTION
	         "SubscriptionWS method wsListPackages ResultCode Specific counters."
	    ::= { subscriptionWSListPackagesEntry 3 }
	    
	-- SUBSCRIPTION-WS METHOD2 wsListPackages END --      
 
	-- SUBSCRIPTION-WS METHOD3 wsListAddOnSubscriptions BEGIN --
	
	subscriptionWSListAddOnSubscriptionsTable OBJECT-TYPE
	       SYNTAX     SEQUENCE OF ListAddOnSubscriptionsSeq
	       MAX-ACCESS not-accessible
	       STATUS     current
	       DESCRIPTION
	             "The (conceptual) table listing the SubscriptionWS Method wsListAddOnSubscriptions ResultCode statistics."
	       ::= { subscriptionWSStatistics 9 }
	       
	ListAddOnSubscriptionsSeq ::= SEQUENCE {		                  
	       listAddOnSubscriptionsResultCode  			Counter32,
	       listAddOnSubscriptionsResultCodeName  		SnmpAdminString,
	       listAddOnSubscriptionsResultCodeCounters  	Counter32       
	}       
		
	subscriptionWSListAddOnSubscriptionsEntry OBJECT-TYPE
	       SYNTAX     ListAddOnSubscriptionsSeq
	       MAX-ACCESS not-accessible
	       STATUS     current
	       DESCRIPTION
	             "An entry (conceptual row) representing a subscriptionWS method wsListAddOnSubscriptions ResultCode specific counters."
	
	       INDEX      { listAddOnSubscriptionsResultCode }
	       ::= { subscriptionWSListAddOnSubscriptionsTable 1 }   
	       
	listAddOnSubscriptionsResultCode OBJECT-TYPE
	       SYNTAX     Integer32 (1..2147483647)
	       MAX-ACCESS not-accessible
	       STATUS     current
	       DESCRIPTION
	             "SubscriptionWS method wsListAddOnSubscriptions ResultCode"
	       ::= { subscriptionWSListAddOnSubscriptionsEntry 1 }       
	   
	listAddOnSubscriptionsResultCodeName OBJECT-TYPE
	    SYNTAX SnmpAdminString
	    MAX-ACCESS read-only
	    STATUS current
	    DESCRIPTION
	         "subscriptionWS wsListAddOnSubscriptions ResultCode Name."
	    ::= { subscriptionWSListAddOnSubscriptionsEntry 2 }
	
	listAddOnSubscriptionsResultCodeCounters OBJECT-TYPE
	    SYNTAX Counter32
	    MAX-ACCESS read-only
	    STATUS current
	    DESCRIPTION
	         "SubscriptionWS method wsListAddOnSubscriptions ResultCode Specific counters."
	    ::= { subscriptionWSListAddOnSubscriptionsEntry 3 }
	    
	-- SUBSCRIPTION-WS METHOD3 wsListAddOnSubscriptions END --      
 
	-- SUBSCRIPTION-WS METHOD4 wsListTopUpSubscriptions BEGIN --
	
	subscriptionWSListTopUpSubscriptionsTable OBJECT-TYPE
	       SYNTAX     SEQUENCE OF ListTopUpSubscriptionsSeq
	       MAX-ACCESS not-accessible
	       STATUS     current
	       DESCRIPTION
	             "The (conceptual) table listing the SubscriptionWS Method wsListTopUpSubscriptions ResultCode statistics."
	       ::= { subscriptionWSStatistics 10 }
	       
	ListTopUpSubscriptionsSeq ::= SEQUENCE {		                  
	       listTopUpSubscriptionsResultCode  			Counter32,
	       listTopUpSubscriptionsResultCodeName  		SnmpAdminString,
	       listTopUpSubscriptionsResultCodeCounters  	Counter32       
	}       
		
	subscriptionWSListTopUpSubscriptionsEntry OBJECT-TYPE
	       SYNTAX     ListTopUpSubscriptionsSeq
	       MAX-ACCESS not-accessible
	       STATUS     current
	       DESCRIPTION
	             "An entry (conceptual row) representing a subscriptionWS method wsListTopUpSubscriptions ResultCode specific counters."
	
	       INDEX      { listTopUpSubscriptionsResultCode }
	       ::= { subscriptionWSListTopUpSubscriptionsTable 1 }   
	       
	listTopUpSubscriptionsResultCode OBJECT-TYPE
	       SYNTAX     Integer32 (1..2147483647)
	       MAX-ACCESS not-accessible
	       STATUS     current
	       DESCRIPTION
	             "SubscriptionWS method wsListTopUpSubscriptions ResultCode"
	       ::= { subscriptionWSListTopUpSubscriptionsEntry 1 }       
	   
	listTopUpSubscriptionsResultCodeName OBJECT-TYPE
	    SYNTAX SnmpAdminString
	    MAX-ACCESS read-only
	    STATUS current
	    DESCRIPTION
	         "subscriptionWS wsListTopUpSubscriptions ResultCode Name."
	    ::= { subscriptionWSListTopUpSubscriptionsEntry 2 }
	
	listTopUpSubscriptionsResultCodeCounters OBJECT-TYPE
	    SYNTAX Counter32
	    MAX-ACCESS read-only
	    STATUS current
	    DESCRIPTION
	         "SubscriptionWS method wsListTopUpSubscriptions ResultCode Specific counters."
	    ::= { subscriptionWSListTopUpSubscriptionsEntry 3 }
	    
	-- SUBSCRIPTION-WS METHOD4 wsListTopUpSubscriptions END --      

	-- SUBSCRIPTION-WS METHOD5 wsChangeAddOnSubscription BEGIN --
	
	subscriptionWSChangeDataAddOnSubscriptionTable OBJECT-TYPE
	       SYNTAX     SEQUENCE OF ChangeDataAddOnSubscriptionSeq
	       MAX-ACCESS not-accessible
	       STATUS     current
	       DESCRIPTION
	             "The (conceptual) table listing the SubscriptionWS Method wsChangeDataAddOnSubscription ResultCode statistics."
	       ::= { subscriptionWSStatistics 11 }
	       
	ChangeDataAddOnSubscriptionSeq ::= SEQUENCE {
	       changeDataAddOnSubscriptionResultCode  			Counter32,
	       changeDataAddOnSubscriptionResultCodeName  		SnmpAdminString,
	       changeDataAddOnSubscriptionResultCodeCounters  	Counter32
	}       
		
	subscriptionWSChangeDataAddOnSubscriptionEntry OBJECT-TYPE
	       SYNTAX     ChangeDataAddOnSubscriptionSeq
	       MAX-ACCESS not-accessible
	       STATUS     current
	       DESCRIPTION
	             "An entry (conceptual row) representing a subscriptionWS method wsChangeDataAddOnSubscription ResultCode specific counters."
	
	       INDEX      { changeDataAddOnSubscriptionResultCode }
	       ::= { subscriptionWSChangeDataAddOnSubscriptionTable 1 }
	       
	changeDataAddOnSubscriptionResultCode OBJECT-TYPE
	       SYNTAX     Integer32 (1..2147483647)
	       MAX-ACCESS not-accessible
	       STATUS     current
	       DESCRIPTION
	             "SubscriptionWS method wsChangeDataAddOnSubscription ResultCode"
	       ::= { subscriptionWSChangeDataAddOnSubscriptionEntry 1 }
	   
	changeDataAddOnSubscriptionResultCodeName OBJECT-TYPE
	    SYNTAX SnmpAdminString
	    MAX-ACCESS read-only
	    STATUS current
	    DESCRIPTION
	         "subscriptionWS wsChangeDataAddOnSubscription ResultCode Name."
	    ::= { subscriptionWSChangeDataAddOnSubscriptionEntry 2 }
	
	changeDataAddOnSubscriptionResultCodeCounters OBJECT-TYPE
	    SYNTAX Counter32
	    MAX-ACCESS read-only
	    STATUS current
	    DESCRIPTION
	         "SubscriptionWS method wsChangeDataAddOnSubscription ResultCode Specific counters."
	    ::= { subscriptionWSChangeDataAddOnSubscriptionEntry 3 }
	    
	-- SUBSCRIPTION-WS METHOD5 wsChangeDataAddOnSubscription END --
    
	-- SUBSCRIPTION-WS METHOD6 wsSubscribeAddOnProductOffer BEGIN --
	
	subscriptionWSSubscribeAddOnProductOfferTable OBJECT-TYPE
	       SYNTAX     SEQUENCE OF SubscribeAddOnProductOfferSeq
	       MAX-ACCESS not-accessible
	       STATUS     current
	       DESCRIPTION
	             "The (conceptual) table listing the SubscriptionWS Method wsSubscribeAddOnProductOffer ResultCode statistics."
	       ::= { subscriptionWSStatistics 12 }
	       
	SubscribeAddOnProductOfferSeq ::= SEQUENCE {
	       subscribeAddOnProductOfferResultCode  			Counter32,
	       subscribeAddOnProductOfferResultCodeName  		SnmpAdminString,
	       subscribeAddOnProductOfferResultCodeCounters  	Counter32
	}       
		
	subscriptionWSSubscribeAddOnProductOfferEntry OBJECT-TYPE
	       SYNTAX     SubscribeAddOnProductOfferSeq
	       MAX-ACCESS not-accessible
	       STATUS     current
	       DESCRIPTION
	             "An entry (conceptual row) representing a subscriptionWS method wsSubscribeAddOnProductOffer ResultCode specific counters."
	
	       INDEX      { subscribeAddOnProductOfferResultCode }
	       ::= { subscriptionWSSubscribeAddOnProductOfferTable 1 }
	       
	subscribeAddOnProductOfferResultCode OBJECT-TYPE
	       SYNTAX     Integer32 (1..2147483647)
	       MAX-ACCESS not-accessible
	       STATUS     current
	       DESCRIPTION
	             "SubscriptionWS method wsSubscribeAddOnProductOffer ResultCode"
	       ::= { subscriptionWSSubscribeAddOnProductOfferEntry 1 }
	   
	subscribeAddOnProductOfferResultCodeName OBJECT-TYPE
	    SYNTAX SnmpAdminString
	    MAX-ACCESS read-only
	    STATUS current
	    DESCRIPTION
	         "subscriptionWS wsSubscribeAddOnProductOffer ResultCode Name."
	    ::= { subscriptionWSSubscribeAddOnProductOfferEntry 2 }
	
	subscribeAddOnProductOfferResultCodeCounters OBJECT-TYPE
	    SYNTAX Counter32
	    MAX-ACCESS read-only
	    STATUS current
	    DESCRIPTION
	         "SubscriptionWS method wsSubscribeAddOnProductOffer ResultCode Specific counters."
	    ::= { subscriptionWSSubscribeAddOnProductOfferEntry 3 }
	    
	-- SUBSCRIPTION-WS METHOD6 wsSubscribeAddOnProductOffer END --

	-- SUBSCRIPTION-WS METHOD7 wsListUsageMonitoringInformation BEGIN --
	
	subscriptionWSListUsageMonitoringInformationTable OBJECT-TYPE
	       SYNTAX     SEQUENCE OF ListUsageMonitoringInformationSeq
	       MAX-ACCESS not-accessible
	       STATUS     current
	       DESCRIPTION
	             "The (conceptual) table listing the SubscriptionWS Method wsListUsageMonitoringInformation ResultCode statistics."
	       ::= { subscriptionWSStatistics 13 }
	       
	ListUsageMonitoringInformationSeq ::= SEQUENCE {		                  
	       listUsageMonitoringInformationResultCode  			Counter32,
	       listUsageMonitoringInformationResultCodeName  		SnmpAdminString,
	       listUsageMonitoringInformationResultCodeCounters  	Counter32       
	}       
		
	subscriptionWSListUsageMonitoringInformationEntry OBJECT-TYPE
	       SYNTAX     ListUsageMonitoringInformationSeq
	       MAX-ACCESS not-accessible
	       STATUS     current
	       DESCRIPTION
	             "An entry (conceptual row) representing a subscriptionWS method wsListUsageMonitoringInformation ResultCode specific counters."
	
	       INDEX      { listUsageMonitoringInformationResultCode }
	       ::= { subscriptionWSListUsageMonitoringInformationTable 1 }   
	       
	listUsageMonitoringInformationResultCode OBJECT-TYPE
	       SYNTAX     Integer32 (1..2147483647)
	       MAX-ACCESS not-accessible
	       STATUS     current
	       DESCRIPTION
	             "SubscriptionWS method wsListUsageMonitoringInformation ResultCode"
	       ::= { subscriptionWSListUsageMonitoringInformationEntry 1 }       
	   
	listUsageMonitoringInformationResultCodeName OBJECT-TYPE
	    SYNTAX SnmpAdminString
	    MAX-ACCESS read-only
	    STATUS current
	    DESCRIPTION
	         "subscriptionWS wsListUsageMonitoringInformation ResultCode Name."
	    ::= { subscriptionWSListUsageMonitoringInformationEntry 2 }
	
	listUsageMonitoringInformationResultCodeCounters OBJECT-TYPE
	    SYNTAX Counter32
	    MAX-ACCESS read-only
	    STATUS current
	    DESCRIPTION
	         "SubscriptionWS method wsListUsageMonitoringInformation ResultCode Specific counters."
	    ::= { subscriptionWSListUsageMonitoringInformationEntry 3 }
	    
	-- SUBSCRIPTION-WS METHOD7 wsListUsageMonitoringInformation END --
	   
	-- SUBSCRIPTION-WS METHOD8 wsGetBalance BEGIN --
	
	subscriptionWSGetBalanceTable OBJECT-TYPE
	       SYNTAX     SEQUENCE OF GetBalanceSeq
	       MAX-ACCESS not-accessible
	       STATUS     current
	       DESCRIPTION
	             "The (conceptual) table listing the SubscriptionWS Method wsGetBalance ResultCode statistics."
	       ::= { subscriptionWSStatistics 14 }
	       
	GetBalanceSeq ::= SEQUENCE {		                  
	       getBalanceResultCode  			Counter32,
	       getBalanceResultCodeName  		SnmpAdminString,
	       getBalanceResultCodeCounters  	Counter32       
	}       
		
	subscriptionWSGetBalanceEntry OBJECT-TYPE
	       SYNTAX     GetBalanceSeq
	       MAX-ACCESS not-accessible
	       STATUS     current
	       DESCRIPTION
	             "An entry (conceptual row) representing a subscriptionWS method wsGetBalance ResultCode specific counters."
	
	       INDEX      { getBalanceResultCode }
	       ::= { subscriptionWSGetBalanceTable 1 }   
	       
	getBalanceResultCode OBJECT-TYPE
	       SYNTAX     Integer32 (1..2147483647)
	       MAX-ACCESS not-accessible
	       STATUS     current
	       DESCRIPTION
	             "SubscriptionWS method wsGetBalance ResultCode"
	       ::= { subscriptionWSGetBalanceEntry 1 }       
	   
	getBalanceResultCodeName OBJECT-TYPE
	    SYNTAX SnmpAdminString
	    MAX-ACCESS read-only
	    STATUS current
	    DESCRIPTION
	         "subscriptionWS wsGetBalance ResultCode Name."
	    ::= { subscriptionWSGetBalanceEntry 2 }
	
	getBalanceResultCodeCounters OBJECT-TYPE
	    SYNTAX Counter32
	    MAX-ACCESS read-only
	    STATUS current
	    DESCRIPTION
	         "SubscriptionWS method wsGetBalance resultCode specific Counters."
	    ::= { subscriptionWSGetBalanceEntry 3 }
	    
	-- SUBSCRIPTION-WS METHOD8 wsGetBalance END --
	    
	-- SUBSCRIPTION-WS METHOD9 wsListTopUpPackages BEGIN --

	subscriptionWSListTopUpPackagesTable OBJECT-TYPE
	       SYNTAX     SEQUENCE OF ListTopUpPackagesSeq
	       MAX-ACCESS not-accessible
	       STATUS     current
	       DESCRIPTION
	             "The (conceptual) table listing the SubscriptionWS Method wsListTopUpPackages ResultCode statistics."
	       ::= { subscriptionWSStatistics 15 }

	ListTopUpPackagesSeq ::= SEQUENCE {
	       listTopUpPackagesResultCode  			Counter32,
	       listTopUpPackagesResultCodeName  		SnmpAdminString,
	       listTopUpPackagesResultCodeCounters  	Counter32
	}

	subscriptionWSListTopUpPackagesEntry OBJECT-TYPE
	       SYNTAX     ListTopUpPackagesSeq
	       MAX-ACCESS not-accessible
	       STATUS     current
	       DESCRIPTION
	             "An entry (conceptual row) representing a subscriptionWS method wsListTopUpPackages ResultCode specific counters."

	       INDEX      { listTopUpPackagesResultCode }
	       ::= { subscriptionWSListTopUpPackagesTable 1 }

	listTopUpPackagesResultCode OBJECT-TYPE
	       SYNTAX     Integer32 (1..2147483647)
	       MAX-ACCESS not-accessible
	       STATUS     current
	       DESCRIPTION
	             "SubscriptionWS method wsListTopUpPackages ResultCode"
	       ::= { subscriptionWSListTopUpPackagesEntry 1 }

	listTopUpPackagesResultCodeName OBJECT-TYPE
	    SYNTAX SnmpAdminString
	    MAX-ACCESS read-only
	    STATUS current
	    DESCRIPTION
	         "subscriptionWS wsListTopUpPackages ResultCode Name."
	    ::= { subscriptionWSListTopUpPackagesEntry 2 }

	listTopUpPackagesResultCodeCounters OBJECT-TYPE
	    SYNTAX Counter32
	    MAX-ACCESS read-only
	    STATUS current
	    DESCRIPTION
	         "SubscriptionWS method wsListTopUpPackages resultCode specific Counters."
	    ::= { subscriptionWSListTopUpPackagesEntry 3 }

	-- SUBSCRIPTION-WS METHOD9 wsListTopUpPackages END --

	-- SUBSCRIPTION-WS METHOD30 wsListBoDPackages BEGIN --

    subscriptionWSListBoDPackagesTable OBJECT-TYPE
           SYNTAX     SEQUENCE OF ListBoDPackagesSeq
           MAX-ACCESS not-accessible
           STATUS     current
           DESCRIPTION
                 "The (conceptual) table listing the SubscriptionWS Method wsListBoDPackages ResultCode statistics."
           ::= { subscriptionWSStatistics 30 }

    ListBoDPackagesSeq ::= SEQUENCE {
           listBoDPackagesResultCode  			Counter32,
           listBoDPackagesResultCodeName  		SnmpAdminString,
           listBoDPackagesResultCodeCounters  	Counter32
    }

    subscriptionWSListBoDPackagesEntry OBJECT-TYPE
           SYNTAX     ListBoDPackagesSeq
           MAX-ACCESS not-accessible
           STATUS     current
           DESCRIPTION
                 "An entry (conceptual row) representing a subscriptionWS method wsListBoDPackages ResultCode specific counters."

           INDEX      { listBoDPackagesResultCode }
           ::= { subscriptionWSListBoDPackagesTable 1 }

    listBoDPackagesResultCode OBJECT-TYPE
           SYNTAX     Integer32 (1..2147483647)
           MAX-ACCESS not-accessible
           STATUS     current
           DESCRIPTION
                 "SubscriptionWS method wsListBoDPackages ResultCode"
           ::= { subscriptionWSListBoDPackagesEntry 1 }

    listBoDPackagesResultCodeName OBJECT-TYPE
        SYNTAX SnmpAdminString
        MAX-ACCESS read-only
        STATUS current
        DESCRIPTION
             "subscriptionWS wsListBoDPackages ResultCode Name."
        ::= { subscriptionWSListBoDPackagesEntry 2 }

    listBoDPackagesResultCodeCounters OBJECT-TYPE
        SYNTAX Counter32
        MAX-ACCESS read-only
        STATUS current
        DESCRIPTION
             "SubscriptionWS method wsListBoDPackages resultCode specific Counters."
        ::= { subscriptionWSListBoDPackagesEntry 3 }

    -- SUBSCRIPTION-WS METHOD30 wsListBoDPackages END --

    -- SUBSCRIPTION-WS METHOD31 fnFGroupMembers BEGIN --

    subscriptionFnFGroupMembersTable OBJECT-TYPE
           SYNTAX     SEQUENCE OF FnFGroupMembersSeq
           MAX-ACCESS not-accessible
           STATUS     current
           DESCRIPTION
                 "The (conceptual) table listing the SubscriptionWS Method FnFGroupMembers ResultCode statistics."
           ::= { subscriptionWSStatistics 31 }

    FnFGroupMembersSeq ::= SEQUENCE {
           fnFGroupMembersResultCode  			Counter32,
           fnFGroupMembersResultCodeName  		SnmpAdminString,
           fnFGroupMembersResultCodeCounters  	Counter32
    }

    subscriptionFnFGroupMembersEntry OBJECT-TYPE
           SYNTAX     FnFGroupMembersSeq
           MAX-ACCESS not-accessible
           STATUS     current
           DESCRIPTION
                 "An entry (conceptual row) representing a subscriptionWS method fnFGroupMembers ResultCode specific counters."

           INDEX      { fnFGroupMembersResultCode }
           ::= { subscriptionFnFGroupMembersTable 1 }

    fnFGroupMembersResultCode OBJECT-TYPE
           SYNTAX     Integer32 (1..2147483647)
           MAX-ACCESS not-accessible
           STATUS     current
           DESCRIPTION
                 "SubscriptionWS method fnFGroupMembers ResultCode"
           ::= { subscriptionFnFGroupMembersEntry 1 }

    fnFGroupMembersResultCodeName OBJECT-TYPE
        SYNTAX SnmpAdminString
        MAX-ACCESS read-only
        STATUS current
        DESCRIPTION
             "subscriptionWS FnFGroupMembers ResultCode Name."
        ::= { subscriptionFnFGroupMembersEntry 2 }

    fnFGroupMembersResultCodeCounters OBJECT-TYPE
        SYNTAX Counter32
        MAX-ACCESS read-only
        STATUS current
        DESCRIPTION
             "SubscriptionWS method FnFGroupMembers resultCode specific Counters."
        ::= { subscriptionFnFGroupMembersEntry 3 }

    -- SUBSCRIPTION-WS METHOD31 fnFGroupMembers END --

	-- SUBSCRIPTION-WS METHOD10 wsSubscribeTopUp BEGIN --
	
	subscriptionWSSubscribeTopUpTable OBJECT-TYPE
	       SYNTAX     SEQUENCE OF SubscribeTopUpSeq
	       MAX-ACCESS not-accessible
	       STATUS     current
	       DESCRIPTION
	             "The (conceptual) table listing the SubscriptionWS Method wsSubscribeTopUp ResultCode statistics."
	       ::= { subscriptionWSStatistics 16 }
	       
	SubscribeTopUpSeq ::= SEQUENCE {		                  
	       subscribeTopUpResultCode  			Counter32,
	       subscribeTopUpResultCodeName  		SnmpAdminString,
	       subscribeTopUpResultCodeCounters  	Counter32       
	}       
		
	subscriptionWSSubscribeTopUpEntry OBJECT-TYPE
	       SYNTAX     SubscribeTopUpSeq
	       MAX-ACCESS not-accessible
	       STATUS     current
	       DESCRIPTION
	             "An entry (conceptual row) representing a subscriptionWS method wsSubscribeTopUp ResultCode specific counters."
	
	       INDEX      { subscribeTopUpResultCode }
	       ::= { subscriptionWSSubscribeTopUpTable 1 }   
	       
	subscribeTopUpResultCode OBJECT-TYPE
	       SYNTAX     Integer32 (1..2147483647)
	       MAX-ACCESS not-accessible
	       STATUS     current
	       DESCRIPTION
	             "SubscriptionWS method wsSubscribeTopUp ResultCode"
	       ::= { subscriptionWSSubscribeTopUpEntry 1 }       
	   
	subscribeTopUpResultCodeName OBJECT-TYPE
	    SYNTAX SnmpAdminString
	    MAX-ACCESS read-only
	    STATUS current
	    DESCRIPTION
	         "subscriptionWS wsSubscribeTopUp ResultCode Name."
	    ::= { subscriptionWSSubscribeTopUpEntry 2 }
	
	subscribeTopUpResultCodeCounters OBJECT-TYPE
	    SYNTAX Counter32
	    MAX-ACCESS read-only
	    STATUS current
	    DESCRIPTION
	         "SubscriptionWS method wsSubscribeTopUp resultCode specific Counters."
	    ::= { subscriptionWSSubscribeTopUpEntry 3 }
	    
	-- SUBSCRIPTION-WS METHOD10 wsSubscribeTopUp END --

	-- SUBSCRIPTION-WS METHOD11 wsChangeTopUpSubscription BEGIN --
	
	subscriptionWSChangeTopUpSubscriptionTable OBJECT-TYPE
	       SYNTAX     SEQUENCE OF ChangeTopUpSubscriptionSeq
	       MAX-ACCESS not-accessible
	       STATUS     current
	       DESCRIPTION
	             "The (conceptual) table listing the SubscriptionWS Method wsChangeTopUpSubscription ResultCode statistics."
	       ::= { subscriptionWSStatistics 17 }
	       
	ChangeTopUpSubscriptionSeq ::= SEQUENCE {		                  
	       changeTopUpSubscriptionResultCode  			Counter32,
	       changeTopUpSubscriptionResultCodeName  		SnmpAdminString,
	       changeTopUpSubscriptionResultCodeCounters  	Counter32       
	}       
		
	subscriptionWSChangeTopUpSubscriptionEntry OBJECT-TYPE
	       SYNTAX     ChangeTopUpSubscriptionSeq
	       MAX-ACCESS not-accessible
	       STATUS     current
	       DESCRIPTION
	             "An entry (conceptual row) representing a subscriptionWS method wsChangeTopUpSubscription ResultCode specific counters."
	
	       INDEX      { changeTopUpSubscriptionResultCode }
	       ::= { subscriptionWSChangeTopUpSubscriptionTable 1 }   
	       
	changeTopUpSubscriptionResultCode OBJECT-TYPE
	       SYNTAX     Integer32 (1..2147483647)
	       MAX-ACCESS not-accessible
	       STATUS     current
	       DESCRIPTION
	             "SubscriptionWS method wsChangeTopUpSubscription ResultCode"
	       ::= { subscriptionWSChangeTopUpSubscriptionEntry 1 }       
	   
	changeTopUpSubscriptionResultCodeName OBJECT-TYPE
	    SYNTAX SnmpAdminString
	    MAX-ACCESS read-only
	    STATUS current
	    DESCRIPTION
	         "subscriptionWS wsChangeTopUpSubscription ResultCode Name."
	    ::= { subscriptionWSChangeTopUpSubscriptionEntry 2 }
	
	changeTopUpSubscriptionResultCodeCounters OBJECT-TYPE
	    SYNTAX Counter32
	    MAX-ACCESS read-only
	    STATUS current
	    DESCRIPTION
	         "SubscriptionWS method wsChangeTopUpSubscription resultCode specific Counters."
	    ::= { subscriptionWSChangeTopUpSubscriptionEntry 3 }
	    
	-- SUBSCRIPTION-WS METHOD11 wsChangeTopUpSubscription END --
-- SUBSCRIPTION-WS METHOD12 wsAddMonetaryBalance BEGIN --

	subscriptionWSAddMonetaryBalanceTable OBJECT-TYPE
	       SYNTAX     SEQUENCE OF AddMonetaryBalanceSeq
	       MAX-ACCESS not-accessible
	       STATUS     current
	       DESCRIPTION
	             "The (conceptual) table listing the SubscriptionWS Method wsAddMonetaryBalance ResultCode statistics."
	       ::= { subscriptionWSStatistics 18 }

	AddMonetaryBalanceSeq ::= SEQUENCE {
	       addMonetaryBalanceResultCode  			Counter32,
	       addMonetaryBalanceResultCodeName  		SnmpAdminString,
	       addMonetaryBalanceResultCodeCounters  	Counter32
	}

	subscriptionWSAddMonetaryBalanceEntry OBJECT-TYPE
	       SYNTAX     AddMonetaryBalanceSeq
	       MAX-ACCESS not-accessible
	       STATUS     current
	       DESCRIPTION
	             "An entry (conceptual row) representing a subscriptionWS method wsAddMonetaryBalance ResultCode specific counters."

	       INDEX      { addMonetaryBalanceResultCode }
	       ::= { subscriptionWSAddMonetaryBalanceTable 1 }

	addMonetaryBalanceResultCode OBJECT-TYPE
	       SYNTAX     Integer32 (1..2147483647)
	       MAX-ACCESS not-accessible
	       STATUS     current
	       DESCRIPTION
	             "SubscriptionWS method wsAddMonetaryBalance ResultCode"
	       ::= { subscriptionWSAddMonetaryBalanceEntry 1 }

	addMonetaryBalanceResultCodeName OBJECT-TYPE
	    SYNTAX SnmpAdminString
	    MAX-ACCESS read-only
	    STATUS current
	    DESCRIPTION
	         "subscriptionWS wsAddMonetaryBalance ResultCode Name."
	    ::= { subscriptionWSAddMonetaryBalanceEntry 2 }

	addMonetaryBalanceResultCodeCounters OBJECT-TYPE
	    SYNTAX Counter32
	    MAX-ACCESS read-only
	    STATUS current
	    DESCRIPTION
	         "SubscriptionWS method wsAddMonetaryBalance resultCode specific Counters."
	    ::= { subscriptionWSAddMonetaryBalanceEntry 3 }

-- SUBSCRIPTION-WS METHOD12 wsAddMonetaryBalance END --

-- SUBSCRIPTION-WS METHOD13 wsGetRnCBalance BEGIN --

	subscriptionWSGetRnCBalanceTable OBJECT-TYPE
	       SYNTAX     SEQUENCE OF GetRnCBalanceSeq
	       MAX-ACCESS not-accessible
	       STATUS     current
	       DESCRIPTION
	             "The (conceptual) table listing the SubscriptionWS Method wsGetRnCBalance ResultCode statistics."
	       ::= { subscriptionWSStatistics 19 }

	GetRnCBalanceSeq ::= SEQUENCE {
	       getRnCBalanceResultCode  			Counter32,
	       getRnCBalanceResultCodeName  		SnmpAdminString,
	       getRnCBalanceResultCodeCounters  	Counter32
	}

	subscriptionWSGetRnCBalanceEntry OBJECT-TYPE
	       SYNTAX     GetRnCBalanceSeq
	       MAX-ACCESS not-accessible
	       STATUS     current
	       DESCRIPTION
	             "An entry (conceptual row) representing a subscriptionWS method wsGetRnCBalance ResultCode specific counters."

	       INDEX      { getRnCBalanceResultCode }
	       ::= { subscriptionWSGetRnCBalanceTable 1 }

	getRnCBalanceResultCode OBJECT-TYPE
	       SYNTAX     Integer32 (1..2147483647)
	       MAX-ACCESS not-accessible
	       STATUS     current
	       DESCRIPTION
	             "SubscriptionWS method wsGetRnCBalance ResultCode"
	       ::= { subscriptionWSGetRnCBalanceEntry 1 }

	getRnCBalanceResultCodeName OBJECT-TYPE
	    SYNTAX SnmpAdminString
	    MAX-ACCESS read-only
	    STATUS current
	    DESCRIPTION
	         "subscriptionWS wsGetRnCBalance ResultCode Name."
	    ::= { subscriptionWSGetRnCBalanceEntry 2 }

	getRnCBalanceResultCodeCounters OBJECT-TYPE
	    SYNTAX Counter32
	    MAX-ACCESS read-only
	    STATUS current
	    DESCRIPTION
	         "SubscriptionWS method wsGetRnCBalance resultCode specific Counters."
	    ::= { subscriptionWSGetRnCBalanceEntry 3 }

-- SUBSCRIPTION-WS METHOD13 wsGetRnCBalance END --

-- SUBSCRIPTION-WS METHOD14 wsChangeRnCAddOnSubscription BEGIN --

	subscriptionWSChangeRnCAddOnSubscriptionTable OBJECT-TYPE
	       SYNTAX     SEQUENCE OF ChangeRnCAddOnSubscriptionSeq
	       MAX-ACCESS not-accessible
	       STATUS     current
	       DESCRIPTION
	             "The (conceptual) table listing the SubscriptionWS Method wsChangeRnCAddOnSubscription ResultCode statistics."
	       ::= { subscriptionWSStatistics 20 }

	ChangeRnCAddOnSubscriptionSeq ::= SEQUENCE {
	       changeRnCAddOnSubscriptionResultCode  			Counter32,
	       changeRnCAddOnSubscriptionResultCodeName  		SnmpAdminString,
	       changeRnCAddOnSubscriptionResultCodeCounters  	Counter32
	}

	subscriptionWSChangeRnCAddOnSubscriptionEntry OBJECT-TYPE
	       SYNTAX     ChangeRnCAddOnSubscriptionSeq
	       MAX-ACCESS not-accessible
	       STATUS     current
	       DESCRIPTION
	             "An entry (conceptual row) representing a subscriptionWS method wsChangeRnCAddOnSubscription ResultCode specific counters."

	       INDEX      { changeRnCAddOnSubscriptionResultCode }
	       ::= { subscriptionWSChangeRnCAddOnSubscriptionTable 1 }

	changeRnCAddOnSubscriptionResultCode OBJECT-TYPE
	       SYNTAX     Integer32 (1..2147483647)
	       MAX-ACCESS not-accessible
	       STATUS     current
	       DESCRIPTION
	             "SubscriptionWS method wsChangeRnCAddOnSubscription ResultCode"
	       ::= { subscriptionWSChangeRnCAddOnSubscriptionEntry 1 }

	changeRnCAddOnSubscriptionResultCodeName OBJECT-TYPE
	    SYNTAX SnmpAdminString
	    MAX-ACCESS read-only
	    STATUS current
	    DESCRIPTION
	         "subscriptionWS wsChangeRnCAddOnSubscription ResultCode Name."
	    ::= { subscriptionWSChangeRnCAddOnSubscriptionEntry 2 }

	changeRnCAddOnSubscriptionResultCodeCounters OBJECT-TYPE
	    SYNTAX Counter32
	    MAX-ACCESS read-only
	    STATUS current
	    DESCRIPTION
	         "SubscriptionWS method wsChangeRnCAddOnSubscription resultCode specific Counters."
	    ::= { subscriptionWSChangeRnCAddOnSubscriptionEntry 3 }

-- SUBSCRIPTION-WS METHOD14 wsChangeRnCAddOnSubscription END --

-- SUBSCRIPTION-WS METHOD15 wsGetMonetayBalance BEGIN --

	subscriptionWSGetMonetaryBalanceTable OBJECT-TYPE
	       SYNTAX     SEQUENCE OF GetMonetaryBalanceSeq
	       MAX-ACCESS not-accessible
	       STATUS     current
	       DESCRIPTION
	             "The (conceptual) table listing the SubscriptionWS Method wsGetMonetaryBalance ResultCode statistics."
	       ::= { subscriptionWSStatistics 21 }

	GetMonetaryBalanceSeq ::= SEQUENCE {
	       getMonetaryBalanceResultCode  			Counter32,
	       getMonetaryBalanceResultCodeName  		SnmpAdminString,
	       getMonetaryBalanceResultCodeCounters  	Counter32
	}

	subscriptionWSGetMonetaryBalanceEntry OBJECT-TYPE
	       SYNTAX     GetMonetaryBalanceSeq
	       MAX-ACCESS not-accessible
	       STATUS     current
	       DESCRIPTION
	             "An entry (conceptual row) representing a subscriptionWS method wsGetMonetaryBalance ResultCode specific counters."

	       INDEX      { getMonetaryBalanceResultCode }
	       ::= { subscriptionWSGetMonetaryBalanceTable 1 }

	getMonetaryBalanceResultCode OBJECT-TYPE
	       SYNTAX     Integer32 (1..2147483647)
	       MAX-ACCESS not-accessible
	       STATUS     current
	       DESCRIPTION
	             "SubscriptionWS method wsGetMonetaryBalance ResultCode"
	       ::= { subscriptionWSGetMonetaryBalanceEntry 1 }

	getMonetaryBalanceResultCodeName OBJECT-TYPE
	    SYNTAX SnmpAdminString
	    MAX-ACCESS read-only
	    STATUS current
	    DESCRIPTION
	         "subscriptionWS wsGetMonetaryBalance ResultCode Name."
	    ::= { subscriptionWSGetMonetaryBalanceEntry 2 }

	getMonetaryBalanceResultCodeCounters OBJECT-TYPE
	    SYNTAX Counter32
	    MAX-ACCESS read-only
	    STATUS current
	    DESCRIPTION
	         "SubscriptionWS method wsGetMonetaryBalance resultCode specific Counters."
	    ::= { subscriptionWSGetMonetaryBalanceEntry 3 }

-- SUBSCRIPTION-WS METHOD15 wsGetMonetaryBalance END --

-- SUBSCRIPTION-WS METHOD16 wsUpdateMonetaryBalance BEGIN --

	subscriptionWSUpdateMonetaryBalanceTable OBJECT-TYPE
	       SYNTAX     SEQUENCE OF UpdateMonetaryBalanceSeq
	       MAX-ACCESS not-accessible
	       STATUS     current
	       DESCRIPTION
	             "The (conceptual) table listing the SubscriptionWS Method wsUpdateMonetaryBalance ResultCode statistics."
	       ::= { subscriptionWSStatistics 22 }

	UpdateMonetaryBalanceSeq ::= SEQUENCE {
	       updateMonetaryBalanceResultCode  			Counter32,
	       updateMonetaryBalanceResultCodeName  		SnmpAdminString,
	       updateMonetaryBalanceResultCodeCounters  	Counter32
	}

	subscriptionWSUpdateMonetaryBalanceEntry OBJECT-TYPE
	       SYNTAX     UpdateMonetaryBalanceSeq
	       MAX-ACCESS not-accessible
	       STATUS     current
	       DESCRIPTION
	             "An entry (conceptual row) representing a subscriptionWS method wsUpdateMonetaryBalance ResultCode specific counters."

	       INDEX      { updateMonetaryBalanceResultCode }
	       ::= { subscriptionWSUpdateMonetaryBalanceTable 1 }

	updateMonetaryBalanceResultCode OBJECT-TYPE
	       SYNTAX     Integer32 (1..2147483647)
	       MAX-ACCESS not-accessible
	       STATUS     current
	       DESCRIPTION
	             "SubscriptionWS method wsUpdateMonetaryBalance ResultCode"
	       ::= { subscriptionWSUpdateMonetaryBalanceEntry 1 }

	updateMonetaryBalanceResultCodeName OBJECT-TYPE
	    SYNTAX SnmpAdminString
	    MAX-ACCESS read-only
	    STATUS current
	    DESCRIPTION
	         "subscriptionWS wsUpdateMonetaryBalance ResultCode Name."
	    ::= { subscriptionWSUpdateMonetaryBalanceEntry 2 }

	updateMonetaryBalanceResultCodeCounters OBJECT-TYPE
	    SYNTAX Counter32
	    MAX-ACCESS read-only
	    STATUS current
	    DESCRIPTION
	         "SubscriptionWS method wsUpdateMonetaryBalance resultCode specific Counters."
	    ::= { subscriptionWSUpdateMonetaryBalanceEntry 3 }

-- SUBSCRIPTION-WS METHOD17 wsUpdateMonetaryBalance END --
-- SUBSCRIPTION-WS METHOD18 wsGetNonMonetaryBalance BEGIN --

	subscriptionWSGetNonMonetaryBalanceTable OBJECT-TYPE
	       SYNTAX     SEQUENCE OF GetNonMonetaryBalanceSeq
	       MAX-ACCESS not-accessible
	       STATUS     current
	       DESCRIPTION
	             "The (conceptual) table listing the SubscriptionWS Method wsGetNonMonetaryBalance ResultCode statistics."
	       ::= { subscriptionWSStatistics 23 }

	GetNonMonetaryBalanceSeq ::= SEQUENCE {
	       getNonMonetaryBalanceResultCode  			Counter32,
	       getNonMonetaryBalanceResultCodeName  		SnmpAdminString,
	       getNonMonetaryBalanceResultCodeCounters  	Counter32
	}

	subscriptionWSGetNonMonetaryBalanceEntry OBJECT-TYPE
	       SYNTAX     GetNonMonetaryBalanceSeq
	       MAX-ACCESS not-accessible
	       STATUS     current
	       DESCRIPTION
	             "An entry (conceptual row) representing a subscriptionWS method wsGetNonMonetaryBalance ResultCode specific counters."

	       INDEX      { getNonMonetaryBalanceResultCode }
	       ::= { subscriptionWSGetNonMonetaryBalanceTable 1 }

	getNonMonetaryBalanceResultCode OBJECT-TYPE
	       SYNTAX     Integer32 (1..2147483647)
	       MAX-ACCESS not-accessible
	       STATUS     current
	       DESCRIPTION
	             "SubscriptionWS method wsGetNonMonetaryBalance ResultCode"
	       ::= { subscriptionWSGetNonMonetaryBalanceEntry 1 }

	getNonMonetaryBalanceResultCodeName OBJECT-TYPE
	    SYNTAX SnmpAdminString
	    MAX-ACCESS read-only
	    STATUS current
	    DESCRIPTION
	         "subscriptionWS wsGetNonMonetaryBalance ResultCode Name."
	    ::= { subscriptionWSGetNonMonetaryBalanceEntry 2 }

	getNonMonetaryBalanceResultCodeCounters OBJECT-TYPE
	    SYNTAX Counter32
	    MAX-ACCESS read-only
	    STATUS current
	    DESCRIPTION
	         "SubscriptionWS method wsGetNonMonetaryBalance resultCode specific Counters."
	    ::= { subscriptionWSGetNonMonetaryBalanceEntry 3 }

-- SUBSCRIPTION-WS METHOD18 wsGetNonMonetaryBalance END --
-- SUBSCRIPTION-WS METHOD19 wsListRnCPackages BEGIN --

	subscriptionWSListRnCPackagesTable OBJECT-TYPE
	       SYNTAX     SEQUENCE OF ListRnCPackagesSeq
	       MAX-ACCESS not-accessible
	       STATUS     current
	       DESCRIPTION
	             "The (conceptual) table listing the SubscriptionWS Method wsListRnCPackages ResultCode statistics."
	       ::= { subscriptionWSStatistics 24 }

	ListRnCPackagesSeq ::= SEQUENCE {
	       listRnCPackagesResultCode  			Counter32,
	       listRnCPackagesResultCodeName  		SnmpAdminString,
	       listRnCPackagesResultCodeCounters  	Counter32
	}

	subscriptionWSListRnCPackagesEntry OBJECT-TYPE
	       SYNTAX     ListRnCPackagesSeq
	       MAX-ACCESS not-accessible
	       STATUS     current
	       DESCRIPTION
	             "An entry (conceptual row) representing a subscriptionWS method wsListRnCPackages ResultCode specific counters."

	       INDEX      { listRnCPackagesResultCode }
	       ::= { subscriptionWSListRnCPackagesTable 1 }

	listRnCPackagesResultCode OBJECT-TYPE
	       SYNTAX     Integer32 (1..2147483647)
	       MAX-ACCESS not-accessible
	       STATUS     current
	       DESCRIPTION
	             "SubscriptionWS method wsListRnCPackages ResultCode"
	       ::= { subscriptionWSListRnCPackagesEntry 1 }

	listRnCPackagesResultCodeName OBJECT-TYPE
	    SYNTAX SnmpAdminString
	    MAX-ACCESS read-only
	    STATUS current
	    DESCRIPTION
	         "subscriptionWS wsListRnCPackages ResultCode Name."
	    ::= { subscriptionWSListRnCPackagesEntry 2 }

	listRnCPackagesResultCodeCounters OBJECT-TYPE
	    SYNTAX Counter32
	    MAX-ACCESS read-only
	    STATUS current
	    DESCRIPTION
	         "SubscriptionWS method wsListRnCPackages resultCode specific Counters."
	    ::= { subscriptionWSListRnCPackagesEntry 3 }

-- SUBSCRIPTION-WS METHOD19 wsListRnCPackages END --

-- SUBSCRIPTION-WS METHOD20 wsSubscribeMonetaryRechargePlan BEGIN --

    	subscriptionWSSubscribeMonetaryRechargePlanTable OBJECT-TYPE
    	       SYNTAX     SEQUENCE OF SubscribeMonetaryRechargePlanSeq
    	       MAX-ACCESS not-accessible
    	       STATUS     current
    	       DESCRIPTION
    	             "The (conceptual) table listing the SubscriptionWS Method wsSubscribeMonetaryRechargePlan ResultCode statistics."
    	       ::= { subscriptionWSStatistics 25 }

    	SubscribeMonetaryRechargePlanSeq ::= SEQUENCE {
    	       subscribeMonetaryRechargePlanResultCode  			Counter32,
    	       subscribeMonetaryRechargePlanResultCodeName  		SnmpAdminString,
    	       subscribeMonetaryRechargePlanResultCodeCounters  	Counter32
    	}

    	subscriptionWSSubscribeMonetaryRechargePlanEntry OBJECT-TYPE
    	       SYNTAX     SubscribeMonetaryRechargePlanSeq
    	       MAX-ACCESS not-accessible
    	       STATUS     current
    	       DESCRIPTION
    	             "An entry (conceptual row) representing a subscriptionWS method wsSubscribeMonetaryRechargePlan ResultCode specific counters."

    	       INDEX      { subscribeMonetaryRechargePlanResultCode }
    	       ::= { subscriptionWSSubscribeMonetaryRechargePlanTable 1 }

    	subscribeMonetaryRechargePlanResultCode OBJECT-TYPE
    	       SYNTAX     Integer32 (1..2147483647)
    	       MAX-ACCESS not-accessible
    	       STATUS     current
    	       DESCRIPTION
    	             "SubscriptionWS method wsSubscribeMonetaryRechargePlan ResultCode"
    	       ::= { subscriptionWSSubscribeMonetaryRechargePlanEntry 1 }

    	subscribeMonetaryRechargePlanResultCodeName OBJECT-TYPE
    	    SYNTAX SnmpAdminString
    	    MAX-ACCESS read-only
    	    STATUS current
    	    DESCRIPTION
    	         "subscriptionWS wsSubscribeMonetaryRechargePlan ResultCode Name."
    	    ::= { subscriptionWSSubscribeMonetaryRechargePlanEntry 2 }

    	subscribeMonetaryRechargePlanResultCodeCounters OBJECT-TYPE
    	    SYNTAX Counter32
    	    MAX-ACCESS read-only
    	    STATUS current
    	    DESCRIPTION
    	         "SubscriptionWS method wsSubscribeMonetaryRechargePlan resultCode specific Counters."
    	    ::= { subscriptionWSSubscribeMonetaryRechargePlanEntry 3 }

-- SUBSCRIPTION-WS METHOD20 wsSubscribeMonetaryRechargePlan END --

-- SUBSCRIPTION-WS METHOD21 wsUpdateCreditLimit BEGIN --

	subscriptionWSUpdateCreditLimitTable OBJECT-TYPE
	       SYNTAX     SEQUENCE OF UpdateCreditLimitSeq
	       MAX-ACCESS not-accessible
	       STATUS     current
	       DESCRIPTION
	             "The (conceptual) table listing the SubscriptionWS Method wsUpdateCreditLimit ResultCode statistics."
	       ::= { subscriptionWSStatistics 26 }

	UpdateCreditLimitSeq ::= SEQUENCE {
	       updateCreditLimitResultCode  			Counter32,
	       updateCreditLimitResultCodeName  		SnmpAdminString,
	       updateCreditLimitResultCodeCounters  	Counter32
	}

	subscriptionWSUpdateCreditLimitEntry OBJECT-TYPE
	       SYNTAX     UpdateCreditLimitSeq
	       MAX-ACCESS not-accessible
	       STATUS     current
	       DESCRIPTION
	             "An entry (conceptual row) representing a subscriptionWS method wsUpdateCreditLimit ResultCode specific counters."

	       INDEX      { updateCreditLimitResultCode }
	       ::= { subscriptionWSUpdateCreditLimitTable 1 }

	updateCreditLimitResultCode OBJECT-TYPE
	       SYNTAX     Integer32 (1..2147483647)
	       MAX-ACCESS not-accessible
	       STATUS     current
	       DESCRIPTION
	             "SubscriptionWS method wsUpdateCreditLimit ResultCode"
	       ::= { subscriptionWSUpdateCreditLimitEntry 1 }

	updateCreditLimitResultCodeName OBJECT-TYPE
	    SYNTAX SnmpAdminString
	    MAX-ACCESS read-only
	    STATUS current
	    DESCRIPTION
	         "subscriptionWS wsUpdateCreditLimit ResultCode Name."
	    ::= { subscriptionWSUpdateCreditLimitEntry 2 }

	updateCreditLimitResultCodeCounters OBJECT-TYPE
	    SYNTAX Counter32
	    MAX-ACCESS read-only
	    STATUS current
	    DESCRIPTION
	         "SubscriptionWS method wsUpdateCreditLimit resultCode specific Counters."
	    ::= { subscriptionWSUpdateCreditLimitEntry 3 }

-- SUBSCRIPTION-WS METHOD21 wsUpdateCreditLimit END --

-- SUBSCRIPTION-WS METHOD23 wsChangeBillDay BEGIN --

	subscriptionWSChangeBillDayTable OBJECT-TYPE
	       SYNTAX     SEQUENCE OF ChangeBillDaySeq
	       MAX-ACCESS not-accessible
	       STATUS     current
	       DESCRIPTION
	             "The (conceptual) table listing the SubscriptionWS Method wsChangeBillDay ResultCode statistics."
	       ::= { subscriptionWSStatistics 28 }

	ChangeBillDaySeq ::= SEQUENCE {
	       changeBillDayResultCode  			Counter32,
	       changeBillDayResultCodeName  		SnmpAdminString,
	       changeBillDayResultCodeCounters  	Counter32
	}

	subscriptionWSChangeBillDayEntry OBJECT-TYPE
	       SYNTAX     ChangeBillDaySeq
	       MAX-ACCESS not-accessible
	       STATUS     current
	       DESCRIPTION
	             "An entry (conceptual row) representing a subscriptionWS method wsChangeBillDay ResultCode specific counters."

	       INDEX      { changeBillDayResultCode }
	       ::= { subscriptionWSChangeBillDayTable 1 }

	changeBillDayResultCode OBJECT-TYPE
	       SYNTAX     Integer32 (1..2147483647)
	       MAX-ACCESS not-accessible
	       STATUS     current
	       DESCRIPTION
	             "SubscriptionWS method wsChangeBillDay ResultCode"
	       ::= { subscriptionWSChangeBillDayEntry 1 }

	changeBillDayResultCodeName OBJECT-TYPE
	    SYNTAX SnmpAdminString
	    MAX-ACCESS read-only
	    STATUS current
	    DESCRIPTION
	         "subscriptionWS wsChangeBillDay ResultCode Name."
	    ::= { subscriptionWSChangeBillDayEntry 2 }

	changeBillDayResultCodeCounters OBJECT-TYPE
	    SYNTAX Counter32
	    MAX-ACCESS read-only
	    STATUS current
	    DESCRIPTION
	         "SubscriptionWS method wsChangeBillDay resultCode specific Counters."
	    ::= { subscriptionWSChangeBillDayEntry 3 }

-- SUBSCRIPTION-WS METHOD23 wsChangeBillDay END --

-- SUBSCRIPTION-WS METHOD22 wsListDataPackages BEGIN --

    subscriptionWSListDataPackagesTable OBJECT-TYPE
           SYNTAX     SEQUENCE OF ListDataPackagesSeq
           MAX-ACCESS not-accessible
           STATUS     current
           DESCRIPTION
                 "The (conceptual) table listing the SubscriptionWS Method wsListDataPackages ResultCode statistics."
           ::= { subscriptionWSStatistics 27 }

    ListDataPackagesSeq ::= SEQUENCE {
           listDataPackagesResultCode  			Counter32,
           listDataPackagesResultCodeName  		SnmpAdminString,
           listDataPackagesResultCodeCounters  	Counter32
    }

    subscriptionWSListDataPackagesEntry OBJECT-TYPE
           SYNTAX     ListDataPackagesSeq
           MAX-ACCESS not-accessible
           STATUS     current
           DESCRIPTION
                 "An entry (conceptual row) representing a subscriptionWS method wsListDataPackages ResultCode specific counters."

           INDEX      { listDataPackagesResultCode }
           ::= { subscriptionWSListDataPackagesTable 1 }

    listDataPackagesResultCode OBJECT-TYPE
           SYNTAX     Integer32 (1..2147483647)
           MAX-ACCESS not-accessible
           STATUS     current
           DESCRIPTION
                 "SubscriptionWS method wsListDataPackages ResultCode"
           ::= { subscriptionWSListDataPackagesEntry 1 }

    listDataPackagesResultCodeName OBJECT-TYPE
        SYNTAX SnmpAdminString
        MAX-ACCESS read-only
        STATUS current
        DESCRIPTION
             "subscriptionWS wsListDataPackages ResultCode Name."
        ::= { subscriptionWSListDataPackagesEntry 2 }

    listDataPackagesResultCodeCounters OBJECT-TYPE
        SYNTAX Counter32
        MAX-ACCESS read-only
        STATUS current
        DESCRIPTION
             "SubscriptionWS method wsListDataPackages ResultCode Specific counters."
        ::= { subscriptionWSListDataPackagesEntry 3 }

-- SUBSCRIPTION-WS METHOD22 wsListDataPackages END --

-- SUBSCRIPTION-WS METHOD24 wsSubscribeBoD BEGIN --

	subscriptionWSSubscribeBoDTable OBJECT-TYPE
	       SYNTAX     SEQUENCE OF SubscribeBoDSeq
	       MAX-ACCESS not-accessible
	       STATUS     current
	       DESCRIPTION
	             "The (conceptual) table listing the SubscriptionWS Method wsSubscribeBoD ResultCode statistics."
	       ::= { subscriptionWSStatistics 29 }

	SubscribeBoDSeq ::= SEQUENCE {
	       subscribeBoDResultCode  			Counter32,
	       subscribeBoDResultCodeName  		SnmpAdminString,
	       subscribeBoDResultCodeCounters  	Counter32
	}

	subscriptionWSSubscribeBoDEntry OBJECT-TYPE
	       SYNTAX     SubscribeBoDSeq
	       MAX-ACCESS not-accessible
	       STATUS     current
	       DESCRIPTION
	             "An entry (conceptual row) representing a subscriptionWS method wsSubscribeBoD ResultCode specific counters."

	       INDEX      { subscribeBoDResultCode }
	       ::= { subscriptionWSSubscribeBoDTable 1 }

	subscribeBoDResultCode OBJECT-TYPE
	       SYNTAX     Integer32 (1..2147483647)
	       MAX-ACCESS not-accessible
	       STATUS     current
	       DESCRIPTION
	             "SubscriptionWS method wsSubscribeBoD ResultCode"
	       ::= { subscriptionWSSubscribeBoDEntry 1 }

	subscribeBoDResultCodeName OBJECT-TYPE
	    SYNTAX SnmpAdminString
	    MAX-ACCESS read-only
	    STATUS current
	    DESCRIPTION
	         "subscriptionWS wsSubscribeBoD ResultCode Name."
	    ::= { subscriptionWSSubscribeBoDEntry 2 }

	subscribeBoDResultCodeCounters OBJECT-TYPE
	    SYNTAX Counter32
	    MAX-ACCESS read-only
	    STATUS current
	    DESCRIPTION
	         "SubscriptionWS method wsSubscribeBoD resultCode specific Counters."
	    ::= { subscriptionWSSubscribeBoDEntry 3 }

-- SUBSCRIPTION-WS METHOD24 wsSubscribeBoD END --


-- SUBSCRIPTION-WS ALL METHOD WISE RESULT CODE END --   
    
-- END of SubscriptionWS
	
-- SubscriberProvisioningWS BEGIN
	
subscriberProvisioningWSStatistics OBJECT IDENTIFIER ::= { netvertexWebServiceStatistics 10 }

subscriberWSTotalRequests OBJECT-TYPE
    SYNTAX Counter32
    MAX-ACCESS read-only
    STATUS current
    DESCRIPTION
         "Total number of SubscriberProvisioningWS requests received by Policy Designer."
    ::= { subscriberProvisioningWSStatistics 1 }

subscriberWSTotalResponses OBJECT-TYPE
    SYNTAX Counter32
    MAX-ACCESS read-only
    STATUS current
    DESCRIPTION
         "Total number of SubscriberProvisioningWS responses given by Policy Designer."
    ::= { subscriberProvisioningWSStatistics 2 }

subscriberWSLastMinuteTotalRequests OBJECT-TYPE
    SYNTAX Counter32
    MAX-ACCESS read-only
    STATUS current
    DESCRIPTION
         "Total number of SubscriberProvisioningWS requests received in Last Minute by Policy Designer."
    ::= { subscriberProvisioningWSStatistics 3 }

subscriberWSAvgTPS OBJECT-TYPE
    SYNTAX Counter32
    MAX-ACCESS read-only
    STATUS current
    DESCRIPTION
         "The average TPS in SubscriberProvisioningWS for last one minute."
    ::= { subscriberProvisioningWSStatistics 4 }
		
subscriberProvisioningWSMethodWiseStatisticsTable OBJECT-TYPE
       SYNTAX     SEQUENCE OF SubscriberProvisioningWSMethodWiseSeq
       MAX-ACCESS not-accessible
       STATUS     current
       DESCRIPTION
             "The (conceptual) table listing the SubscriberProvisioningWS method wise counters."
       ::= { subscriberProvisioningWSStatistics 5 }
       
SubscriberProvisioningWSMethodWiseSeq ::= SEQUENCE {
       subscriberWSMethodIndex   			Integer32,
       subscriberWSMethodName     			SnmpAdminString,
       subscriberWSMethodTotalRequests      Counter32,
       subscriberWSMethodTotalResponses     Counter32,
       subscriberWSMethodLastMinuteTotalRequests	Counter32,
       subscriberWSMethodAvgTPS             Counter32
 }       
	
subscriberProvisioningWSMethodWiseEntry OBJECT-TYPE
       SYNTAX     SubscriberProvisioningWSMethodWiseSeq
       MAX-ACCESS not-accessible
       STATUS     current
       DESCRIPTION
             "An entry (conceptual row) representing a SubscriberProvisioningWS
              method wise counters."

       INDEX      { subscriberWSMethodIndex }
       ::= { subscriberProvisioningWSMethodWiseStatisticsTable 1 }
       
subscriberWSMethodIndex OBJECT-TYPE
       SYNTAX     Integer32 (1..2147483647)
       MAX-ACCESS not-accessible
       STATUS     current
       DESCRIPTION
             "SubscriberProvisioningWS method's Index."
       ::= { subscriberProvisioningWSMethodWiseEntry 1 }
   
subscriberWSMethodName OBJECT-TYPE
       SYNTAX     SnmpAdminString
       MAX-ACCESS read-only
       STATUS     current
       DESCRIPTION
             "SubscriberProvisioningWS method's Name"
       ::= { subscriberProvisioningWSMethodWiseEntry 2 }
       
subscriberWSMethodTotalRequests OBJECT-TYPE
    SYNTAX Counter32
    MAX-ACCESS read-only
    STATUS current
    DESCRIPTION
         "Total number of SubscriberProvisioningWS method wise Requests received by Policy Designer."
    ::= { subscriberProvisioningWSMethodWiseEntry 3 }

subscriberWSMethodTotalResponses OBJECT-TYPE
    SYNTAX Counter32
    MAX-ACCESS read-only
    STATUS current
    DESCRIPTION
         "Total number of SubscriberProvisioningWS method wise Responses given by Policy Designer."
    ::= { subscriberProvisioningWSMethodWiseEntry 4 }

subscriberWSMethodLastMinuteTotalRequests OBJECT-TYPE
    SYNTAX Counter32
    MAX-ACCESS read-only
    STATUS current
    DESCRIPTION
         "Total number of SubscriberProvisioningWS method wise Requests received in Last Minute by Policy Designer."
    ::= { subscriberProvisioningWSMethodWiseEntry 5 }

subscriberWSMethodAvgTPS OBJECT-TYPE
    SYNTAX Counter32
    MAX-ACCESS read-only
    STATUS current
    DESCRIPTION
         "Method's average TPS in SubscriberProvisioningWS for last one minute."
    ::= { subscriberProvisioningWSMethodWiseEntry 6 }
       
       
-- SUBSCRIBER-PROVISIONING-WS RESULT CODE COUNTERS BEGIN --
       
subscriberProvisioningWSResultCodeWiseStatisticsTable OBJECT-TYPE
       SYNTAX     SEQUENCE OF SubscriberWSResultCodeWiseSeq
       MAX-ACCESS not-accessible
       STATUS     current
       DESCRIPTION
             "The (conceptual) table listing the SubscriberProvisioningWS ResultCodes statistics."
       ::= { subscriberProvisioningWSStatistics 6 }
       
SubscriberWSResultCodeWiseSeq ::= SEQUENCE {             
       subscriberWSResultCode  			Counter32,
       subscriberWSResultCodeName  		SnmpAdminString,
       subscriberWSResultCodeCounters  	Counter32       
}       
	
subscriberWSResultCodeWiseEntry OBJECT-TYPE
       SYNTAX     SubscriberWSResultCodeWiseSeq
       MAX-ACCESS not-accessible
       STATUS     current
       DESCRIPTION
             "An entry (conceptual row) representing a SubscriberProvisioningWS ResultCode specific statistics."

       INDEX      { subscriberWSResultCode }
       ::= { subscriberProvisioningWSResultCodeWiseStatisticsTable 1 }   
       
subscriberWSResultCode OBJECT-TYPE
       SYNTAX     Integer32 (1..2147483647)
       MAX-ACCESS not-accessible
       STATUS     current
       DESCRIPTION
             "SubscriberProvisioningWS ResultCode."
       ::= { subscriberWSResultCodeWiseEntry 1 }       
   
subscriberWSResultCodeName OBJECT-TYPE
    SYNTAX SnmpAdminString
    MAX-ACCESS read-only
    STATUS current
    DESCRIPTION
         "SubscriberProvisioningWS ResultCode Name."
    ::= { subscriberWSResultCodeWiseEntry 2 }

subscriberWSResultCodeCounters OBJECT-TYPE
    SYNTAX Counter32
    MAX-ACCESS read-only
    STATUS current
    DESCRIPTION
         "SubscriberProvisioningWS ResultCode statistics."
    ::= { subscriberWSResultCodeWiseEntry 3 }
    
-- SUBSCRIBER-PROVISIONING-WS RESULT CODE STATISTICS END --
   
-- SUBSCRIBER-PROVISIONING-WS METHOD WISE RESULT CODE BEGIN --

	-- SUBSCRIBER-PROVISIONING-WS METHOD1 wSAddSubscriberProfile BEGIN --
	
	subscriberProvisioningWSAddSubscriberProfileTable OBJECT-TYPE
	       SYNTAX     SEQUENCE OF SubscriberWSAddSubscriberProfileSeq
	       MAX-ACCESS not-accessible
	       STATUS     current
	       DESCRIPTION
	             "The (conceptual) table listing the SubscriberProvisioningWS Method wSAddSubscriberProfile ResultCodes statistics."
	       ::= { subscriberProvisioningWSStatistics 7 }
	       
	SubscriberWSAddSubscriberProfileSeq ::= SEQUENCE {		                  
	       addSubscriberProfileResultCode  			Counter32,
	       addSubscriberProfileResultCodeName  		SnmpAdminString,
	       addSubscriberProfileResultCodeCounters  	Counter32       
	}       
		
	subscriberWSAddSubscriberProfileEntry OBJECT-TYPE
	       SYNTAX     SubscriberWSAddSubscriberProfileSeq
	       MAX-ACCESS not-accessible
	       STATUS     current
	       DESCRIPTION
	             "An entry (conceptual row) representing a SubscriberProvisioningWS Method wSAddSubscriberProfile ResultCode specific statistics."
	
	       INDEX      { addSubscriberProfileResultCode }
	       ::= { subscriberProvisioningWSAddSubscriberProfileTable 1 }   
	       
	addSubscriberProfileResultCode OBJECT-TYPE
	       SYNTAX     Integer32 (1..2147483647)
	       MAX-ACCESS not-accessible
	       STATUS     current
	       DESCRIPTION
	             "SubscriberProvisioningWS method wSAddSubscriberProfile ResultCode."
	       ::= { subscriberWSAddSubscriberProfileEntry 1 }       
	   
	addSubscriberProfileResultCodeName OBJECT-TYPE
	    SYNTAX SnmpAdminString
	    MAX-ACCESS read-only
	    STATUS current
	    DESCRIPTION
	         "SubscriberProvisioningWS method wSAddSubscriberProfile ResultCode Name."
	    ::= { subscriberWSAddSubscriberProfileEntry 2 }
	
	addSubscriberProfileResultCodeCounters OBJECT-TYPE
	    SYNTAX Counter32
	    MAX-ACCESS read-only
	    STATUS current
	    DESCRIPTION
	         "SubscriberProvisioningWS method wSAddSubscriberProfile ResultCode Specific statistics."
	    ::= { subscriberWSAddSubscriberProfileEntry 3 }
	    
    -- SUBSCRIBER-PROVISIONING-WS METHOD1 wSAddSubscriberProfile END --
    
	-- SUBSCRIBER-PROVISIONING-WS METHOD2 wsUpdateSubscriberProfile BEGIN --
	
	subscriberProvisioningWSUpdateSubscriberProfileTable OBJECT-TYPE
	       SYNTAX     SEQUENCE OF SubscriberWSUpdateSubscriberProfileSeq
	       MAX-ACCESS not-accessible
	       STATUS     current
	       DESCRIPTION
	             "The (conceptual) table listing the SubscriberProvisioningWS Method wsUpdateSubscriberProfile ResultCodes statistics."
	       ::= { subscriberProvisioningWSStatistics 8 }
	       
	SubscriberWSUpdateSubscriberProfileSeq ::= SEQUENCE {		                  
	       updateSubscriberProfileResultCode  			Counter32,
	       updateSubscriberProfileResultCodeName  		SnmpAdminString,
	       updateSubscriberProfileResultCodeCounters  	Counter32       
	}       
		
	subscriberWSUpdateSubscriberProfileEntry OBJECT-TYPE
	       SYNTAX     SubscriberWSUpdateSubscriberProfileSeq
	       MAX-ACCESS not-accessible
	       STATUS     current
	       DESCRIPTION
	             "An entry (conceptual row) representing a SubscriberProvisioningWS Method wsUpdateSubscriberProfile ResultCode specific statistics."
	
	       INDEX      { updateSubscriberProfileResultCode }
	       ::= { subscriberProvisioningWSUpdateSubscriberProfileTable 1 }   
	       
	updateSubscriberProfileResultCode OBJECT-TYPE
	       SYNTAX     Integer32 (1..2147483647)
	       MAX-ACCESS not-accessible
	       STATUS     current
	       DESCRIPTION
	             "SubscriberProvisioningWS method wsUpdateSubscriberProfile ResultCode."
	       ::= { subscriberWSUpdateSubscriberProfileEntry 1 }       
	   
	updateSubscriberProfileResultCodeName OBJECT-TYPE
	    SYNTAX SnmpAdminString
	    MAX-ACCESS read-only
	    STATUS current
	    DESCRIPTION
	         "SubscriberProvisioningWS method wsUpdateSubscriberProfile ResultCode Name."
	    ::= { subscriberWSUpdateSubscriberProfileEntry 2 }
	
	updateSubscriberProfileResultCodeCounters OBJECT-TYPE
	    SYNTAX Counter32
	    MAX-ACCESS read-only
	    STATUS current
	    DESCRIPTION
	         "SubscriberProvisioningWS method wsUpdateSubscriberProfile ResultCode Specific statistics."
	    ::= { subscriberWSUpdateSubscriberProfileEntry 3 }
	    
    -- SUBSCRIBER-PROVISIONING-WS METHOD2 wsUpdateSubscriberProfile END --

	-- SUBSCRIBER-PROVISIONING-WS METHOD3 wsDeleteSubscriberProfile BEGIN --
	
	subscriberProvisioningWSDeleteSubscriberProfileTable OBJECT-TYPE
	       SYNTAX     SEQUENCE OF SubscriberWSDeleteSubscriberProfileSeq
	       MAX-ACCESS not-accessible
	       STATUS     current
	       DESCRIPTION
	             "The (conceptual) table listing the SubscriberProvisioningWS Method wsDeleteSubscriberProfile ResultCodes statistics."
	       ::= { subscriberProvisioningWSStatistics 9 }
	       
	SubscriberWSDeleteSubscriberProfileSeq ::= SEQUENCE {		                  
	       deleteSubscriberProfileResultCode  			Counter32,
	       deleteSubscriberProfileResultCodeName  		SnmpAdminString,
	       deleteSubscriberProfileResultCodeCounters  	Counter32       
	}       
		
	subscriberWSDeleteSubscriberProfileEntry OBJECT-TYPE
	       SYNTAX     SubscriberWSDeleteSubscriberProfileSeq
	       MAX-ACCESS not-accessible
	       STATUS     current
	       DESCRIPTION
	             "An entry (conceptual row) representing a SubscriberProvisioningWS Method wsDeleteSubscriberProfile ResultCode specific statistics."
	
	       INDEX      { deleteSubscriberProfileResultCode }
	       ::= { subscriberProvisioningWSDeleteSubscriberProfileTable 1 }   
	       
	deleteSubscriberProfileResultCode OBJECT-TYPE
	       SYNTAX     Integer32 (1..2147483647)
	       MAX-ACCESS not-accessible
	       STATUS     current
	       DESCRIPTION
	             "SubscriberProvisioningWS method wsDeleteSubscriberProfile ResultCode."
	       ::= { subscriberWSDeleteSubscriberProfileEntry 1 }       
	   
	deleteSubscriberProfileResultCodeName OBJECT-TYPE
	    SYNTAX SnmpAdminString
	    MAX-ACCESS read-only
	    STATUS current
	    DESCRIPTION
	         "SubscriberProvisioningWS method wsDeleteSubscriberProfile ResultCode Name."
	    ::= { subscriberWSDeleteSubscriberProfileEntry 2 }
	
	deleteSubscriberProfileResultCodeCounters OBJECT-TYPE
	    SYNTAX Counter32
	    MAX-ACCESS read-only
	    STATUS current
	    DESCRIPTION
	         "SubscriberProvisioningWS method wsDeleteSubscriberProfile ResultCode Specific statistics."
	    ::= { subscriberWSDeleteSubscriberProfileEntry 3 }
	    
    -- SUBSCRIBER-PROVISIONING-WS METHOD3 wsDeleteSubscriberProfile END --

	-- SUBSCRIBER-PROVISIONING-WS METHOD4 wsDeleteSubscriberProfiles BEGIN --
	
	subscriberProvisioningWSDeleteSubscriberProfilesTable OBJECT-TYPE
	       SYNTAX     SEQUENCE OF SubscriberWSDeleteSubscriberProfilesSeq
	       MAX-ACCESS not-accessible
	       STATUS     current
	       DESCRIPTION
	             "The (conceptual) table listing the SubscriberProvisioningWS Method wsDeleteSubscriberProfiles ResultCodes statistics."
	       ::= { subscriberProvisioningWSStatistics 10 }
	       
	SubscriberWSDeleteSubscriberProfilesSeq ::= SEQUENCE {		                  
	       deleteSubscriberProfilesResultCode  			Counter32,
	       deleteSubscriberProfilesResultCodeName  		SnmpAdminString,
	       deleteSubscriberProfilesResultCodeCounters  	Counter32       
	}       
		
	subscriberWSDeleteSubscriberProfilesEntry OBJECT-TYPE
	       SYNTAX     SubscriberWSDeleteSubscriberProfilesSeq
	       MAX-ACCESS not-accessible
	       STATUS     current
	       DESCRIPTION
	             "An entry (conceptual row) representing a SubscriberProvisioningWS Method wsDeleteSubscriberProfiles ResultCode specific statistics."
	
	       INDEX      { deleteSubscriberProfilesResultCode }
	       ::= { subscriberProvisioningWSDeleteSubscriberProfilesTable 1 }   
	       
	deleteSubscriberProfilesResultCode OBJECT-TYPE
	       SYNTAX     Integer32 (1..2147483647)
	       MAX-ACCESS not-accessible
	       STATUS     current
	       DESCRIPTION
	             "SubscriberProvisioningWS method wsDeleteSubscriberProfiles ResultCode."
	       ::= { subscriberWSDeleteSubscriberProfilesEntry 1 }       
	   
	deleteSubscriberProfilesResultCodeName OBJECT-TYPE
	    SYNTAX SnmpAdminString
	    MAX-ACCESS read-only
	    STATUS current
	    DESCRIPTION
	         "SubscriberProvisioningWS method wsDeleteSubscriberProfiles ResultCode Name."
	    ::= { subscriberWSDeleteSubscriberProfilesEntry 2 }
	
	deleteSubscriberProfilesResultCodeCounters OBJECT-TYPE
	    SYNTAX Counter32
	    MAX-ACCESS read-only
	    STATUS current
	    DESCRIPTION
	         "SubscriberProvisioningWS method wsDeleteSubscriberProfiles ResultCode Specific statistics."
	    ::= { subscriberWSDeleteSubscriberProfilesEntry 3 }
	    
    -- SUBSCRIBER-PROVISIONING-WS METHOD4 wsDeleteSubscriberProfiles END --

	-- SUBSCRIBER-PROVISIONING-WS METHOD5 wsAddSubscriberBulk BEGIN --
	
	subscriberProvisioningWSAddSubscriberBulkTable OBJECT-TYPE
	       SYNTAX     SEQUENCE OF SubscriberWSAddSubscriberBulkSeq
	       MAX-ACCESS not-accessible
	       STATUS     current
	       DESCRIPTION
	             "The (conceptual) table listing the SubscriberProvisioningWS Method wsAddSubscriberBulk ResultCodes statistics."
	       ::= { subscriberProvisioningWSStatistics 11 }
	       
	SubscriberWSAddSubscriberBulkSeq ::= SEQUENCE {		                  
	       addSubscriberBulkResultCode  			Counter32,
	       addSubscriberBulkResultCodeName  		SnmpAdminString,
	       addSubscriberBulkResultCodeCounters  	Counter32       
	}       
		
	subscriberWSAddSubscriberBulkEntry OBJECT-TYPE
	       SYNTAX     SubscriberWSAddSubscriberBulkSeq
	       MAX-ACCESS not-accessible
	       STATUS     current
	       DESCRIPTION
	             "An entry (conceptual row) representing a SubscriberProvisioningWS Method wsAddSubscriberBulk ResultCode specific statistics."
	
	       INDEX      { addSubscriberBulkResultCode }
	       ::= { subscriberProvisioningWSAddSubscriberBulkTable 1 }   
	       
	addSubscriberBulkResultCode OBJECT-TYPE
	       SYNTAX     Integer32 (1..2147483647)
	       MAX-ACCESS not-accessible
	       STATUS     current
	       DESCRIPTION
	             "SubscriberProvisioningWS method wsAddSubscriberBulk ResultCode."
	       ::= { subscriberWSAddSubscriberBulkEntry 1 }       
	   
	addSubscriberBulkResultCodeName OBJECT-TYPE
	    SYNTAX SnmpAdminString
	    MAX-ACCESS read-only
	    STATUS current
	    DESCRIPTION
	         "SubscriberProvisioningWS method wsAddSubscriberBulk ResultCode Name."
	    ::= { subscriberWSAddSubscriberBulkEntry 2 }
	
	addSubscriberBulkResultCodeCounters OBJECT-TYPE
	    SYNTAX Counter32
	    MAX-ACCESS read-only
	    STATUS current
	    DESCRIPTION
	         "SubscriberProvisioningWS method wsAddSubscriberBulk ResultCode Specific statistics."
	    ::= { subscriberWSAddSubscriberBulkEntry 3 }
	    
    -- SUBSCRIBER-PROVISIONING-WS METHOD5 wsAddSubscriberBulk END --

	-- SUBSCRIBER-PROVISIONING-WS METHOD6 wsGetSubscriberProfileByID BEGIN --
	
	subscriberProvisioningWSGetSubscriberProfileByIDTable OBJECT-TYPE
	       SYNTAX     SEQUENCE OF SubscriberWSGetSubscriberProfileByIDSeq
	       MAX-ACCESS not-accessible
	       STATUS     current
	       DESCRIPTION
	             "The (conceptual) table listing the SubscriberProvisioningWS Method wsGetSubscriberProfileByID ResultCodes statistics."
	       ::= { subscriberProvisioningWSStatistics 12 }
	       
	SubscriberWSGetSubscriberProfileByIDSeq ::= SEQUENCE {		                  
	       getSubscriberProfileByIDResultCode  			Counter32,
	       getSubscriberProfileByIDResultCodeName  		SnmpAdminString,
	       getSubscriberProfileByIDResultCodeCounters  	Counter32       
	}       
		
	subscriberWSGetSubscriberProfileByIDEntry OBJECT-TYPE
	       SYNTAX     SubscriberWSGetSubscriberProfileByIDSeq
	       MAX-ACCESS not-accessible
	       STATUS     current
	       DESCRIPTION
	             "An entry (conceptual row) representing a SubscriberProvisioningWS Method wsGetSubscriberProfileByID ResultCode specific statistics."
	
	       INDEX      { getSubscriberProfileByIDResultCode }
	       ::= { subscriberProvisioningWSGetSubscriberProfileByIDTable 1 }   
	       
	getSubscriberProfileByIDResultCode OBJECT-TYPE
	       SYNTAX     Integer32 (1..2147483647)
	       MAX-ACCESS not-accessible
	       STATUS     current
	       DESCRIPTION
	             "SubscriberProvisioningWS method wsGetSubscriberProfileByID ResultCode."
	       ::= { subscriberWSGetSubscriberProfileByIDEntry 1 }       
	   
	getSubscriberProfileByIDResultCodeName OBJECT-TYPE
	    SYNTAX SnmpAdminString
	    MAX-ACCESS read-only
	    STATUS current
	    DESCRIPTION
	         "SubscriberProvisioningWS method wsGetSubscriberProfileByID ResultCode Name."
	    ::= { subscriberWSGetSubscriberProfileByIDEntry 2 }
	
	getSubscriberProfileByIDResultCodeCounters OBJECT-TYPE
	    SYNTAX Counter32
	    MAX-ACCESS read-only
	    STATUS current
	    DESCRIPTION
	         "SubscriberProvisioningWS method wsGetSubscriberProfileByID ResultCode Specific statistics."
	    ::= { subscriberWSGetSubscriberProfileByIDEntry 3 }
	    
    -- SUBSCRIBER-PROVISIONING-WS METHOD6 wsGetSubscriberProfileByID END --

	-- SUBSCRIBER-PROVISIONING-WS METHOD7 wsListSubscriberProfiles BEGIN --
	
	subscriberProvisioningWSListSubscriberProfilesTable OBJECT-TYPE
	       SYNTAX     SEQUENCE OF SubscriberWSListSubscriberProfilesSeq
	       MAX-ACCESS not-accessible
	       STATUS     current
	       DESCRIPTION
	             "The (conceptual) table listing the SubscriberProvisioningWS Method wsListSubscriberProfiles ResultCodes statistics."
	       ::= { subscriberProvisioningWSStatistics 13 }
	       
	SubscriberWSListSubscriberProfilesSeq ::= SEQUENCE {		                  
	       listSubscriberProfilesResultCode  			Counter32,
	       listSubscriberProfilesResultCodeName  		SnmpAdminString,
	       listSubscriberProfilesResultCodeCounters  	Counter32       
	}       
		
	subscriberWSListSubscriberProfilesEntry OBJECT-TYPE
	       SYNTAX     SubscriberWSListSubscriberProfilesSeq
	       MAX-ACCESS not-accessible
	       STATUS     current
	       DESCRIPTION
	             "An entry (conceptual row) representing a SubscriberProvisioningWS Method wsListSubscriberProfiles ResultCode specific statistics."
	
	       INDEX      { listSubscriberProfilesResultCode }
	       ::= { subscriberProvisioningWSListSubscriberProfilesTable 1 }   
	       
	listSubscriberProfilesResultCode OBJECT-TYPE
	       SYNTAX     Integer32 (1..2147483647)
	       MAX-ACCESS not-accessible
	       STATUS     current
	       DESCRIPTION
	             "SubscriberProvisioningWS method wsListSubscriberProfiles ResultCode."
	       ::= { subscriberWSListSubscriberProfilesEntry 1 }       
	   
	listSubscriberProfilesResultCodeName OBJECT-TYPE
	    SYNTAX SnmpAdminString
	    MAX-ACCESS read-only
	    STATUS current
	    DESCRIPTION
	         "SubscriberProvisioningWS method wsListSubscriberProfiles ResultCode Name."
	    ::= { subscriberWSListSubscriberProfilesEntry 2 }
	
	listSubscriberProfilesResultCodeCounters OBJECT-TYPE
	    SYNTAX Counter32
	    MAX-ACCESS read-only
	    STATUS current
	    DESCRIPTION
	         "SubscriberProvisioningWS method wsListSubscriberProfiles ResultCode Specific statistics."
	    ::= { subscriberWSListSubscriberProfilesEntry 3 }
	    
    -- SUBSCRIBER-PROVISIONING-WS METHOD7 wsListSubscriberProfiles END --

	-- SUBSCRIBER-PROVISIONING-WS METHOD8 wsPurgeSubscriber BEGIN --
	
	subscriberProvisioningWSPurgeSubscriberTable OBJECT-TYPE
	       SYNTAX     SEQUENCE OF SubscriberWSPurgeSubscriberSeq
	       MAX-ACCESS not-accessible
	       STATUS     current
	       DESCRIPTION
	             "The (conceptual) table listing the SubscriberProvisioningWS Method wsPurgeSubscriber ResultCodes statistics."
	       ::= { subscriberProvisioningWSStatistics 14 }
	       
	SubscriberWSPurgeSubscriberSeq ::= SEQUENCE {		                  
	       purgeSubscriberResultCode  			Counter32,
	       purgeSubscriberResultCodeName  		SnmpAdminString,
	       purgeSubscriberResultCodeCounters  	Counter32       
	}       
		
	subscriberWSPurgeSubscriberEntry OBJECT-TYPE
	       SYNTAX     SubscriberWSPurgeSubscriberSeq
	       MAX-ACCESS not-accessible
	       STATUS     current
	       DESCRIPTION
	             "An entry (conceptual row) representing a SubscriberProvisioningWS Method wsPurgeSubscriber ResultCode specific statistics."
	
	       INDEX      { purgeSubscriberResultCode }
	       ::= { subscriberProvisioningWSPurgeSubscriberTable 1 }   
	       
	purgeSubscriberResultCode OBJECT-TYPE
	       SYNTAX     Integer32 (1..2147483647)
	       MAX-ACCESS not-accessible
	       STATUS     current
	       DESCRIPTION
	             "SubscriberProvisioningWS method wsPurgeSubscriber ResultCode."
	       ::= { subscriberWSPurgeSubscriberEntry 1 }       
	   
	purgeSubscriberResultCodeName OBJECT-TYPE
	    SYNTAX SnmpAdminString
	    MAX-ACCESS read-only
	    STATUS current
	    DESCRIPTION
	         "SubscriberProvisioningWS method wsPurgeSubscriber ResultCode Name."
	    ::= { subscriberWSPurgeSubscriberEntry 2 }
	
	purgeSubscriberResultCodeCounters OBJECT-TYPE
	    SYNTAX Counter32
	    MAX-ACCESS read-only
	    STATUS current
	    DESCRIPTION
	         "SubscriberProvisioningWS method wsPurgeSubscriber ResultCode Specific statistics."
	    ::= { subscriberWSPurgeSubscriberEntry 3 }
	    
    -- SUBSCRIBER-PROVISIONING-WS METHOD8 wsPurgeSubscriber END --

	-- SUBSCRIBER-PROVISIONING-WS METHOD9 wsPurgeSubscribers BEGIN --
	
	subscriberProvisioningWSPurgeSubscribersTable OBJECT-TYPE
	       SYNTAX     SEQUENCE OF SubscriberWSPurgeSubscribersSeq
	       MAX-ACCESS not-accessible
	       STATUS     current
	       DESCRIPTION
	             "The (conceptual) table listing the SubscriberProvisioningWS Method wsPurgeSubscribers ResultCodes statistics."
	       ::= { subscriberProvisioningWSStatistics 15 }
	       
	SubscriberWSPurgeSubscribersSeq ::= SEQUENCE {		                  
	       purgeSubscribersResultCode  			Counter32,
	       purgeSubscribersResultCodeName  		SnmpAdminString,
	       purgeSubscribersResultCodeCounters  	Counter32       
	}       
		
	subscriberWSPurgeSubscribersEntry OBJECT-TYPE
	       SYNTAX     SubscriberWSPurgeSubscribersSeq
	       MAX-ACCESS not-accessible
	       STATUS     current
	       DESCRIPTION
	             "An entry (conceptual row) representing a SubscriberProvisioningWS Method wsPurgeSubscribers ResultCode specific statistics."
	
	       INDEX      { purgeSubscribersResultCode }
	       ::= { subscriberProvisioningWSPurgeSubscribersTable 1 }   
	       
	purgeSubscribersResultCode OBJECT-TYPE
	       SYNTAX     Integer32 (1..2147483647)
	       MAX-ACCESS not-accessible
	       STATUS     current
	       DESCRIPTION
	             "SubscriberProvisioningWS method wsPurgeSubscribers ResultCode."
	       ::= { subscriberWSPurgeSubscribersEntry 1 }       
	   
	purgeSubscribersResultCodeName OBJECT-TYPE
	    SYNTAX SnmpAdminString
	    MAX-ACCESS read-only
	    STATUS current
	    DESCRIPTION
	         "SubscriberProvisioningWS method wsPurgeSubscribers ResultCode Name."
	    ::= { subscriberWSPurgeSubscribersEntry 2 }
	
	purgeSubscribersResultCodeCounters OBJECT-TYPE
	    SYNTAX Counter32
	    MAX-ACCESS read-only
	    STATUS current
	    DESCRIPTION
	         "SubscriberProvisioningWS method wsPurgeSubscribers ResultCode Specific statistics."
	    ::= { subscriberWSPurgeSubscribersEntry 3 }
	    
    -- SUBSCRIBER-PROVISIONING-WS METHOD9 wsPurgeSubscribers END --

	-- SUBSCRIBER-PROVISIONING-WS METHOD10 wsPurgeAllSubscriber BEGIN --
	
	subscriberProvisioningWSPurgeAllSubscriberTable OBJECT-TYPE
	       SYNTAX     SEQUENCE OF SubscriberWSPurgeAllSubscriberSeq
	       MAX-ACCESS not-accessible
	       STATUS     current
	       DESCRIPTION
	             "The (conceptual) table listing the SubscriberProvisioningWS Method wsPurgeAllSubscriber ResultCodes statistics."
	       ::= { subscriberProvisioningWSStatistics 16 }
	       
	SubscriberWSPurgeAllSubscriberSeq ::= SEQUENCE {		                  
	       purgeAllSubscriberResultCode  			Counter32,
	       purgeAllSubscriberResultCodeName  		SnmpAdminString,
	       purgeAllSubscriberResultCodeCounters  	Counter32       
	}       
		
	subscriberWSPurgeAllSubscriberEntry OBJECT-TYPE
	       SYNTAX     SubscriberWSPurgeAllSubscriberSeq
	       MAX-ACCESS not-accessible
	       STATUS     current
	       DESCRIPTION
	             "An entry (conceptual row) representing a SubscriberProvisioningWS Method wsPurgeAllSubscriber ResultCode specific statistics."
	
	       INDEX      { purgeAllSubscriberResultCode }
	       ::= { subscriberProvisioningWSPurgeAllSubscriberTable 1 }   
	       
	purgeAllSubscriberResultCode OBJECT-TYPE
	       SYNTAX     Integer32 (1..2147483647)
	       MAX-ACCESS not-accessible
	       STATUS     current
	       DESCRIPTION
	             "SubscriberProvisioningWS method wsPurgeAllSubscriber ResultCode."
	       ::= { subscriberWSPurgeAllSubscriberEntry 1 }       
	   
	purgeAllSubscriberResultCodeName OBJECT-TYPE
	    SYNTAX SnmpAdminString
	    MAX-ACCESS read-only
	    STATUS current
	    DESCRIPTION
	         "SubscriberProvisioningWS method wsPurgeAllSubscriber ResultCode Name."
	    ::= { subscriberWSPurgeAllSubscriberEntry 2 }
	
	purgeAllSubscriberResultCodeCounters OBJECT-TYPE
	    SYNTAX Counter32
	    MAX-ACCESS read-only
	    STATUS current
	    DESCRIPTION
	         "SubscriberProvisioningWS method wsPurgeAllSubscriber ResultCode Specific statistics."
	    ::= { subscriberWSPurgeAllSubscriberEntry 3 }
	    
    -- SUBSCRIBER-PROVISIONING-WS METHOD10 wsPurgeAllSubscriber END --

	-- SUBSCRIBER-PROVISIONING-WS METHOD11 wsRestoreSubscriber BEGIN --
	
	subscriberProvisioningWSRestoreSubscriberTable OBJECT-TYPE
	       SYNTAX     SEQUENCE OF SubscriberWSRestoreSubscriberSeq
	       MAX-ACCESS not-accessible
	       STATUS     current
	       DESCRIPTION
	             "The (conceptual) table listing the SubscriberProvisioningWS Method wsRestoreSubscriber ResultCodes statistics."
	       ::= { subscriberProvisioningWSStatistics 17 }
	       
	SubscriberWSRestoreSubscriberSeq ::= SEQUENCE {		                  
	       restoreSubscriberResultCode  			Counter32,
	       restoreSubscriberResultCodeName  		SnmpAdminString,
	       restoreSubscriberResultCodeCounters  	Counter32       
	}       
		
	subscriberWSRestoreSubscriberEntry OBJECT-TYPE
	       SYNTAX     SubscriberWSRestoreSubscriberSeq
	       MAX-ACCESS not-accessible
	       STATUS     current
	       DESCRIPTION
	             "An entry (conceptual row) representing a SubscriberProvisioningWS Method wsRestoreSubscriber ResultCode specific statistics."
	
	       INDEX      { restoreSubscriberResultCode }
	       ::= { subscriberProvisioningWSRestoreSubscriberTable 1 }   
	       
	restoreSubscriberResultCode OBJECT-TYPE
	       SYNTAX     Integer32 (1..2147483647)
	       MAX-ACCESS not-accessible
	       STATUS     current
	       DESCRIPTION
	             "SubscriberProvisioningWS method wsRestoreSubscriber ResultCode."
	       ::= { subscriberWSRestoreSubscriberEntry 1 }       
	   
	restoreSubscriberResultCodeName OBJECT-TYPE
	    SYNTAX SnmpAdminString
	    MAX-ACCESS read-only
	    STATUS current
	    DESCRIPTION
	         "SubscriberProvisioningWS method wsRestoreSubscriber ResultCode Name."
	    ::= { subscriberWSRestoreSubscriberEntry 2 }
	
	restoreSubscriberResultCodeCounters OBJECT-TYPE
	    SYNTAX Counter32
	    MAX-ACCESS read-only
	    STATUS current
	    DESCRIPTION
	         "SubscriberProvisioningWS method wsRestoreSubscriber ResultCode Specific statistics."
	    ::= { subscriberWSRestoreSubscriberEntry 3 }
	    
    -- SUBSCRIBER-PROVISIONING-WS METHOD11 wsRestoreSubscriber END --

	-- SUBSCRIBER-PROVISIONING-WS METHOD12 wsRestoreSubscribers BEGIN --
	
	subscriberProvisioningWSRestoreSubscribersTable OBJECT-TYPE
	       SYNTAX     SEQUENCE OF SubscriberWSRestoreSubscribersSeq
	       MAX-ACCESS not-accessible
	       STATUS     current
	       DESCRIPTION
	             "The (conceptual) table listing the SubscriberProvisioningWS Method wsRestoreSubscribers ResultCodes statistics."
	       ::= { subscriberProvisioningWSStatistics 18 }
	       
	SubscriberWSRestoreSubscribersSeq ::= SEQUENCE {		                  
	       restoreSubscribersResultCode  			Counter32,
	       restoreSubscribersResultCodeName  		SnmpAdminString,
	       restoreSubscribersResultCodeCounters  	Counter32       
	}       
		
	subscriberWSRestoreSubscribersEntry OBJECT-TYPE
	       SYNTAX     SubscriberWSRestoreSubscribersSeq
	       MAX-ACCESS not-accessible
	       STATUS     current
	       DESCRIPTION
	             "An entry (conceptual row) representing a SubscriberProvisioningWS Method wsRestoreSubscribers ResultCode specific statistics."
	
	       INDEX      { restoreSubscribersResultCode }
	       ::= { subscriberProvisioningWSRestoreSubscribersTable 1 }   
	       
	restoreSubscribersResultCode OBJECT-TYPE
	       SYNTAX     Integer32 (1..2147483647)
	       MAX-ACCESS not-accessible
	       STATUS     current
	       DESCRIPTION
	             "SubscriberProvisioningWS method wsRestoreSubscribers ResultCode."
	       ::= { subscriberWSRestoreSubscribersEntry 1 }       
	   
	restoreSubscribersResultCodeName OBJECT-TYPE
	    SYNTAX SnmpAdminString
	    MAX-ACCESS read-only
	    STATUS current
	    DESCRIPTION
	         "SubscriberProvisioningWS method wsRestoreSubscribers ResultCode Name."
	    ::= { subscriberWSRestoreSubscribersEntry 2 }
	
	restoreSubscribersResultCodeCounters OBJECT-TYPE
	    SYNTAX Counter32
	    MAX-ACCESS read-only
	    STATUS current
	    DESCRIPTION
	         "SubscriberProvisioningWS method wsRestoreSubscribers ResultCode Specific statistics."
	    ::= { subscriberWSRestoreSubscribersEntry 3 }
	    
    -- SUBSCRIBER-PROVISIONING-WS METHOD12 wsRestoreSubscribers END --

	-- SUBSCRIBER-PROVISIONING-WS METHOD13 wsMigrateSubscriber BEGIN --
	
	subscriberProvisioningWSMigrateSubscriberTable OBJECT-TYPE
	       SYNTAX     SEQUENCE OF SubscriberWSMigrateSubscriberSeq
	       MAX-ACCESS not-accessible
	       STATUS     current
	       DESCRIPTION
	             "The (conceptual) table listing the SubscriberProvisioningWS Method wsMigrateSubscriber ResultCodes statistics."
	       ::= { subscriberProvisioningWSStatistics 19 }
	       
	SubscriberWSMigrateSubscriberSeq ::= SEQUENCE {		                  
	       migrateSubscriberResultCode  			Counter32,
	       migrateSubscriberResultCodeName  		SnmpAdminString,
	       migrateSubscriberResultCodeCounters  	Counter32       
	}       
		
	subscriberWSMigrateSubscriberEntry OBJECT-TYPE
	       SYNTAX     SubscriberWSMigrateSubscriberSeq
	       MAX-ACCESS not-accessible
	       STATUS     current
	       DESCRIPTION
	             "An entry (conceptual row) representing a SubscriberProvisioningWS Method wsMigrateSubscriber ResultCode specific statistics."
	
	       INDEX      { migrateSubscriberResultCode }
	       ::= { subscriberProvisioningWSMigrateSubscriberTable 1 }   
	       
	migrateSubscriberResultCode OBJECT-TYPE
	       SYNTAX     Integer32 (1..2147483647)
	       MAX-ACCESS not-accessible
	       STATUS     current
	       DESCRIPTION
	             "SubscriberProvisioningWS method wsMigrateSubscriber ResultCode."
	       ::= { subscriberWSMigrateSubscriberEntry 1 }       
	   
	migrateSubscriberResultCodeName OBJECT-TYPE
	    SYNTAX SnmpAdminString
	    MAX-ACCESS read-only
	    STATUS current
	    DESCRIPTION
	         "SubscriberProvisioningWS method wsMigrateSubscriber ResultCode Name."
	    ::= { subscriberWSMigrateSubscriberEntry 2 }
	
	migrateSubscriberResultCodeCounters OBJECT-TYPE
	    SYNTAX Counter32
	    MAX-ACCESS read-only
	    STATUS current
	    DESCRIPTION
	         "SubscriberProvisioningWS method wsMigrateSubscriber ResultCode Specific statistics."
	    ::= { subscriberWSMigrateSubscriberEntry 3 }
	    
    -- SUBSCRIBER-PROVISIONING-WS METHOD13 wsRestoreSubscribers END --

	-- SUBSCRIBER-PROVISIONING-WS METHOD14 wsAddSubscriber BEGIN --
	
	subscriberProvisioningWSAddSubscriberTable OBJECT-TYPE
	       SYNTAX     SEQUENCE OF SubscriberWSAddSubscriberSeq
	       MAX-ACCESS not-accessible
	       STATUS     current
	       DESCRIPTION
	             "The (conceptual) table listing the SubscriberProvisioningWS Method wsAddSubscriber ResultCodes statistics."
	       ::= { subscriberProvisioningWSStatistics 20 }
	       
	SubscriberWSAddSubscriberSeq ::= SEQUENCE {		                  
	       addSubscriberResultCode  			Counter32,
	       addSubscriberResultCodeName  		SnmpAdminString,
	       addSubscriberResultCodeCounters  	Counter32       
	}       
		
	subscriberWSAddSubscriberEntry OBJECT-TYPE
	       SYNTAX     SubscriberWSAddSubscriberSeq
	       MAX-ACCESS not-accessible
	       STATUS     current
	       DESCRIPTION
	             "An entry (conceptual row) representing a SubscriberProvisioningWS Method wsAddSubscriber ResultCode specific statistics."
	
	       INDEX      { addSubscriberResultCode }
	       ::= { subscriberProvisioningWSAddSubscriberTable 1 }   
	       
	addSubscriberResultCode OBJECT-TYPE
	       SYNTAX     Integer32 (1..2147483647)
	       MAX-ACCESS not-accessible
	       STATUS     current
	       DESCRIPTION
	             "SubscriberProvisioningWS method wsAddSubscriber ResultCode."
	       ::= { subscriberWSAddSubscriberEntry 1 }       
	   
	addSubscriberResultCodeName OBJECT-TYPE
	    SYNTAX SnmpAdminString
	    MAX-ACCESS read-only
	    STATUS current
	    DESCRIPTION
	         "SubscriberProvisioningWS method wsAddSubscriber ResultCode Name."
	    ::= { subscriberWSAddSubscriberEntry 2 }
	
	addSubscriberResultCodeCounters OBJECT-TYPE
	    SYNTAX Counter32
	    MAX-ACCESS read-only
	    STATUS current
	    DESCRIPTION
	         "SubscriberProvisioningWS method wsAddSubscriber ResultCode Specific statistics."
	    ::= { subscriberWSAddSubscriberEntry 3 }
	    
    -- SUBSCRIBER-PROVISIONING-WS METHOD14 wsAddSubscriber END --

	-- SUBSCRIBER-PROVISIONING-WS METHOD15 wsAddSubscribers BEGIN --
	
	subscriberProvisioningWSAddSubscribersTable OBJECT-TYPE
	       SYNTAX     SEQUENCE OF SubscriberWSAddSubscribersSeq
	       MAX-ACCESS not-accessible
	       STATUS     current
	       DESCRIPTION
	             "The (conceptual) table listing the SubscriberProvisioningWS Method wsAddSubscribers ResultCodes statistics."
	       ::= { subscriberProvisioningWSStatistics 21 }
	       
	SubscriberWSAddSubscribersSeq ::= SEQUENCE {		                  
	       addSubscribersResultCode  			Counter32,
	       addSubscribersResultCodeName  		SnmpAdminString,
	       addSubscribersResultCodeCounters  	Counter32       
	}       
		
	subscriberWSAddSubscribersEntry OBJECT-TYPE
	       SYNTAX     SubscriberWSAddSubscribersSeq
	       MAX-ACCESS not-accessible
	       STATUS     current
	       DESCRIPTION
	             "An entry (conceptual row) representing a SubscriberProvisioningWS Method wsAddSubscribers ResultCode specific statistics."
	
	       INDEX      { addSubscribersResultCode }
	       ::= { subscriberProvisioningWSAddSubscribersTable 1 }   
	       
	addSubscribersResultCode OBJECT-TYPE
	       SYNTAX     Integer32 (1..2147483647)
	       MAX-ACCESS not-accessible
	       STATUS     current
	       DESCRIPTION
	             "SubscriberProvisioningWS method wsAddSubscribers ResultCode."
	       ::= { subscriberWSAddSubscribersEntry 1 }       
	   
	addSubscribersResultCodeName OBJECT-TYPE
	    SYNTAX SnmpAdminString
	    MAX-ACCESS read-only
	    STATUS current
	    DESCRIPTION
	         "SubscriberProvisioningWS method wsAddSubscribers ResultCode Name."
	    ::= { subscriberWSAddSubscribersEntry 2 }
	
	addSubscribersResultCodeCounters OBJECT-TYPE
	    SYNTAX Counter32
	    MAX-ACCESS read-only
	    STATUS current
	    DESCRIPTION
	         "SubscriberProvisioningWS method wsAddSubscribers ResultCode Specific statistics."
	    ::= { subscriberWSAddSubscribersEntry 3 }
	    
    -- SUBSCRIBER-PROVISIONING-WS METHOD15 wsAddSubscribers END --

-- SUBSCRIBER-PROVISIONING-WS METHOD wsChangeImsPackage BEGIN --

    	subscriberProvisioningWSChangeImsPackageTable OBJECT-TYPE
    	       SYNTAX     SEQUENCE OF SubscriberWSChangeImsPackageSeq
    	       MAX-ACCESS not-accessible
    	       STATUS     current
    	       DESCRIPTION
    	             "The (conceptual) table listing the SubscriberProvisioningWS Method wsChangeImsPackage ResultCodes statistics."
    	       ::= { subscriberProvisioningWSStatistics 22 }

    	SubscriberWSChangeImsPackageSeq ::= SEQUENCE {
    	       changeImsPackageResultCode  			Counter32,
    	       changeImsPackageResultCodeName  		SnmpAdminString,
    	       changeImsPackageResultCodeCounters  	Counter32
    	}

    	subscriberWSChangeImsPackageEntry OBJECT-TYPE
    	       SYNTAX     SubscriberWSChangeImsPackageSeq
    	       MAX-ACCESS not-accessible
    	       STATUS     current
    	       DESCRIPTION
    	             "An entry (conceptual row) representing a SubscriberProvisioningWS Method wsChangeImsPackage ResultCode specific statistics."

    	       INDEX      { changeImsPackageResultCode }
    	       ::= { subscriberProvisioningWSChangeImsPackageTable 1 }

    	changeImsPackageResultCode OBJECT-TYPE
    	       SYNTAX     Integer32 (1..2147483647)
    	       MAX-ACCESS not-accessible
    	       STATUS     current
    	       DESCRIPTION
    	             "SubscriberProvisioningWS method wsChangeImsPackage ResultCode."
    	       ::= { subscriberWSChangeImsPackageEntry 1 }

    	changeImsPackageResultCodeName OBJECT-TYPE
    	    SYNTAX SnmpAdminString
    	    MAX-ACCESS read-only
    	    STATUS current
    	    DESCRIPTION
    	         "SubscriberProvisioningWS method wsChangeImsPackage ResultCode Name."
    	    ::= { subscriberWSChangeImsPackageEntry 2 }

    	changeImsPackageResultCodeCounters OBJECT-TYPE
    	    SYNTAX Counter32
    	    MAX-ACCESS read-only
    	    STATUS current
    	    DESCRIPTION
    	         "SubscriberProvisioningWS method wsChangeImsPackage ResultCode Specific statistics."
    	    ::= { subscriberWSChangeImsPackageEntry 3 }

-- SUBSCRIBER-PROVISIONING-WS METHOD wsChangeImsPackage END --
-- SUBSCRIBER-PROVISIONING-WS METHOD wsChangeBaseProductOffer BEGIN --

    	subscriberProvisioningWSChangeBaseProductOfferTable OBJECT-TYPE
    	       SYNTAX     SEQUENCE OF SubscriberWSChangeBaseProductOfferSeq
    	       MAX-ACCESS not-accessible
    	       STATUS     current
    	       DESCRIPTION
    	             "The (conceptual) table listing the SubscriberProvisioningWS Method wsChangeBaseProductOffer ResultCodes statistics."
    	       ::= { subscriberProvisioningWSStatistics 23 }

    	SubscriberWSChangeBaseProductOfferSeq ::= SEQUENCE {
    	       changeBaseProductOfferResultCode  			Counter32,
    	       changeBaseProductOfferResultCodeName  		SnmpAdminString,
    	       changeBaseProductOfferResultCodeCounters  	Counter32
    	}

    	subscriberWSChangeBaseProductOfferEntry OBJECT-TYPE
    	       SYNTAX     SubscriberWSChangeBaseProductOfferSeq
    	       MAX-ACCESS not-accessible
    	       STATUS     current
    	       DESCRIPTION
    	             "An entry (conceptual row) representing a SubscriberProvisioningWS Method wsChangeBaseProductOffer ResultCode specific statistics."

    	       INDEX      { changeBaseProductOfferResultCode }
    	       ::= { subscriberProvisioningWSChangeBaseProductOfferTable 1 }

    	changeBaseProductOfferResultCode OBJECT-TYPE
    	       SYNTAX     Integer32 (1..2147483647)
    	       MAX-ACCESS not-accessible
    	       STATUS     current
    	       DESCRIPTION
    	             "SubscriberProvisioningWS method wsChangeBaseProductOffer ResultCode."
    	       ::= { subscriberWSChangeBaseProductOfferEntry 1 }

    	changeBaseProductOfferResultCodeName OBJECT-TYPE
    	    SYNTAX SnmpAdminString
    	    MAX-ACCESS read-only
    	    STATUS current
    	    DESCRIPTION
    	         "SubscriberProvisioningWS method wsChangeBaseProductOffer ResultCode Name."
    	    ::= { subscriberWSChangeBaseProductOfferEntry 2 }

    	changeBaseProductOfferResultCodeCounters OBJECT-TYPE
    	    SYNTAX Counter32
    	    MAX-ACCESS read-only
    	    STATUS current
    	    DESCRIPTION
    	         "SubscriberProvisioningWS method wsChangeBaseProductOffer ResultCode Specific statistics."
    	    ::= { subscriberWSChangeBaseProductOfferEntry 3 }

-- SUBSCRIBER-PROVISIONING-WS METHOD wsChangeBaseProductOffer END --

-- SUBSCRIBER-PROVISIONING-WS METHOD wsAddAlternateId BEGIN --

	subscriberProvisioningWSAddAlternateIdTable OBJECT-TYPE
	       SYNTAX     SEQUENCE OF SubscriberWSAddAlternateIdSeq
	       MAX-ACCESS not-accessible
	       STATUS     current
	       DESCRIPTION
	             "The (conceptual) table listing the SubscriberProvisioningWS Method wsAddAlternateId ResultCodes statistics."
	       ::= { subscriberProvisioningWSStatistics 24 }

	SubscriberWSAddAlternateIdSeq ::= SEQUENCE {
	       addAlternateIdResultCode  			Counter32,
	       addAlternateIdResultCodeName  		SnmpAdminString,
	       addAlternateIdResultCodeCounters  	Counter32
	}

	subscriberWSAddAlternateIdEntry OBJECT-TYPE
	       SYNTAX     SubscriberWSAddAlternateIdSeq
	       MAX-ACCESS not-accessible
	       STATUS     current
	       DESCRIPTION
	             "An entry (conceptual row) representing a SubscriberProvisioningWS Method wsAddAlternateId ResultCode specific statistics."

	       INDEX      { addAlternateIdResultCode }
	       ::= { subscriberProvisioningWSAddAlternateIdTable 1 }

	addAlternateIdResultCode OBJECT-TYPE
	       SYNTAX     Integer32 (1..2147483647)
	       MAX-ACCESS not-accessible
	       STATUS     current
	       DESCRIPTION
	             "SubscriberProvisioningWS method wsAddAlternateId ResultCode."
	       ::= { subscriberWSAddAlternateIdEntry 1 }

	addAlternateIdResultCodeName OBJECT-TYPE
	    SYNTAX SnmpAdminString
	    MAX-ACCESS read-only
	    STATUS current
	    DESCRIPTION
	         "SubscriberProvisioningWS method wsAddAlternateId ResultCode Name."
	    ::= { subscriberWSAddAlternateIdEntry 2 }

	addAlternateIdResultCodeCounters OBJECT-TYPE
	    SYNTAX Counter32
	    MAX-ACCESS read-only
	    STATUS current
	    DESCRIPTION
	         "SubscriberProvisioningWS method wsAddAlternateId ResultCode Specific statistics."
	    ::= { subscriberWSAddAlternateIdEntry 3 }

   -- SUBSCRIBER-PROVISIONING-WS METHOD wsAddAlternateId END --

   -- SUBSCRIBER-PROVISIONING-WS METHOD wsUpdateAlternateId BEGIN --

   	subscriberProvisioningWSUpdateAlternateIdTable OBJECT-TYPE
   	       SYNTAX     SEQUENCE OF SubscriberWSUpdateAlternateIdSeq
   	       MAX-ACCESS not-accessible
   	       STATUS     current
   	       DESCRIPTION
   	             "The (conceptual) table listing the SubscriberProvisioningWS Method wsUpdateAlternateId ResultCodes statistics."
   	       ::= { subscriberProvisioningWSStatistics 25 }

   	SubscriberWSUpdateAlternateIdSeq ::= SEQUENCE {
   	       updateAlternateIdResultCode  			Counter32,
   	       updateAlternateIdResultCodeName  		SnmpAdminString,
   	       updateAlternateIdResultCodeCounters  	Counter32
   	}

   	subscriberWSUpdateAlternateIdEntry OBJECT-TYPE
   	       SYNTAX     SubscriberWSUpdateAlternateIdSeq
   	       MAX-ACCESS not-accessible
   	       STATUS     current
   	       DESCRIPTION
   	             "An entry (conceptual row) representing a SubscriberProvisioningWS Method wsUpdateAlternateId ResultCode specific statistics."

   	       INDEX      { updateAlternateIdResultCode }
   	       ::= { subscriberProvisioningWSUpdateAlternateIdTable 1 }

   	updateAlternateIdResultCode OBJECT-TYPE
   	       SYNTAX     Integer32 (1..2147483647)
   	       MAX-ACCESS not-accessible
   	       STATUS     current
   	       DESCRIPTION
   	             "SubscriberProvisioningWS method wsUpdateAlternateId ResultCode."
   	       ::= { subscriberWSUpdateAlternateIdEntry 1 }

   	updateAlternateIdResultCodeName OBJECT-TYPE
   	    SYNTAX SnmpAdminString
   	    MAX-ACCESS read-only
   	    STATUS current
   	    DESCRIPTION
   	         "SubscriberProvisioningWS method wsUpdateAlternateId ResultCode Name."
   	    ::= { subscriberWSUpdateAlternateIdEntry 2 }

   	updateAlternateIdResultCodeCounters OBJECT-TYPE
   	    SYNTAX Counter32
   	    MAX-ACCESS read-only
   	    STATUS current
   	    DESCRIPTION
   	         "SubscriberProvisioningWS method wsUpdateAlternateId ResultCode Specific statistics."
   	    ::= { subscriberWSUpdateAlternateIdEntry 3 }

      -- SUBSCRIBER-PROVISIONING-WS METHOD wsUpdateAlternateId END --

  -- SUBSCRIBER-PROVISIONING-WS METHOD wsChangeAlternateIdStatus BEGIN --

   	subscriberProvisioningWSChangeAlternateIdStatusTable OBJECT-TYPE
   	       SYNTAX     SEQUENCE OF SubscriberWSChangeAlternateIdStatusSeq
   	       MAX-ACCESS not-accessible
   	       STATUS     current
   	       DESCRIPTION
   	             "The (conceptual) table listing the SubscriberProvisioningWS Method wsChangeAlternateIdStatus ResultCodes statistics."
   	       ::= { subscriberProvisioningWSStatistics 26 }

   	SubscriberWSChangeAlternateIdStatusSeq ::= SEQUENCE {
   	       changeAlternateIdStatusResultCode  			Counter32,
   	       changeAlternateIdStatusResultCodeName  		SnmpAdminString,
   	       changeAlternateIdStatusResultCodeCounters  	Counter32
   	}

   	subscriberWSChangeAlternateIdStatusEntry OBJECT-TYPE
   	       SYNTAX     SubscriberWSChangeAlternateIdStatusSeq
   	       MAX-ACCESS not-accessible
   	       STATUS     current
   	       DESCRIPTION
   	             "An entry (conceptual row) representing a SubscriberProvisioningWS Method wsChangeAlternateIdStatus ResultCode specific statistics."

   	       INDEX      { changeAlternateIdStatusResultCode }
   	       ::= { subscriberProvisioningWSChangeAlternateIdStatusTable 1 }

   	changeAlternateIdStatusResultCode OBJECT-TYPE
   	       SYNTAX     Integer32 (1..2147483647)
   	       MAX-ACCESS not-accessible
   	       STATUS     current
   	       DESCRIPTION
   	             "SubscriberProvisioningWS method wsChangeAlternateIdStatus ResultCode."
   	       ::= { subscriberWSChangeAlternateIdStatusEntry 1 }

   	changeAlternateIdStatusResultCodeName OBJECT-TYPE
   	    SYNTAX SnmpAdminString
   	    MAX-ACCESS read-only
   	    STATUS current
   	    DESCRIPTION
   	         "SubscriberProvisioningWS method wsChangeAlternateIdStatus ResultCode Name."
   	    ::= { subscriberWSChangeAlternateIdStatusEntry 2 }

   	changeAlternateIdStatusResultCodeCounters OBJECT-TYPE
   	    SYNTAX Counter32
   	    MAX-ACCESS read-only
   	    STATUS current
   	    DESCRIPTION
   	         "SubscriberProvisioningWS method wsChangeAlternateIdStatus ResultCode Specific statistics."
   	    ::= { subscriberWSChangeAlternateIdStatusEntry 3 }

      -- SUBSCRIBER-PROVISIONING-WS METHOD wsChangeAlternateIdStatus END --


  -- SUBSCRIBER-PROVISIONING-WS METHOD wsDeleteAlternateId BEGIN --

   	subscriberProvisioningWSDeleteAlternateIdTable OBJECT-TYPE
   	       SYNTAX     SEQUENCE OF SubscriberWSDeleteAlternateIdSeq
   	       MAX-ACCESS not-accessible
   	       STATUS     current
   	       DESCRIPTION
   	             "The (conceptual) table listing the SubscriberProvisioningWS Method wsDeleteAlternateId ResultCodes statistics."
   	       ::= { subscriberProvisioningWSStatistics 27 }

   	SubscriberWSDeleteAlternateIdSeq ::= SEQUENCE {
   	       deleteAlternateIdResultCode  			Counter32,
   	       deleteAlternateIdResultCodeName  		SnmpAdminString,
   	       deleteAlternateIdResultCodeCounters  	Counter32
   	}

   	subscriberWSDeleteAlternateIdEntry OBJECT-TYPE
   	       SYNTAX     SubscriberWSDeleteAlternateIdSeq
   	       MAX-ACCESS not-accessible
   	       STATUS     current
   	       DESCRIPTION
   	             "An entry (conceptual row) representing a SubscriberProvisioningWS Method wsDeleteAlternateId ResultCode specific statistics."

   	       INDEX      { deleteAlternateIdResultCode }
   	       ::= { subscriberProvisioningWSDeleteAlternateIdTable 1 }

   	deleteAlternateIdResultCode OBJECT-TYPE
   	       SYNTAX     Integer32 (1..2147483647)
   	       MAX-ACCESS not-accessible
   	       STATUS     current
   	       DESCRIPTION
   	             "SubscriberProvisioningWS method wsDeleteAlternateId ResultCode."
   	       ::= { subscriberWSDeleteAlternateIdEntry 1 }

   	deleteAlternateIdResultCodeName OBJECT-TYPE
   	    SYNTAX SnmpAdminString
   	    MAX-ACCESS read-only
   	    STATUS current
   	    DESCRIPTION
   	         "SubscriberProvisioningWS method wsDeleteAlternateId ResultCode Name."
   	    ::= { subscriberWSDeleteAlternateIdEntry 2 }

   	deleteAlternateIdResultCodeCounters OBJECT-TYPE
   	    SYNTAX Counter32
   	    MAX-ACCESS read-only
   	    STATUS current
   	    DESCRIPTION
   	         "SubscriberProvisioningWS method wsDeleteAlternateId ResultCode Specific statistics."
   	    ::= { subscriberWSDeleteAlternateIdEntry 3 }

      -- SUBSCRIBER-PROVISIONING-WS METHOD wsDeleteAlternateId END --

  -- SUBSCRIBER-PROVISIONING-WS METHOD wsGetAlternateId BEGIN --

   	subscriberProvisioningWSGetAlternateIdTable OBJECT-TYPE
   	       SYNTAX     SEQUENCE OF SubscriberWSGetAlternateIdSeq
   	       MAX-ACCESS not-accessible
   	       STATUS     current
   	       DESCRIPTION
   	             "The (conceptual) table listing the SubscriberProvisioningWS Method wsGetAlternateId ResultCodes statistics."
   	       ::= { subscriberProvisioningWSStatistics 28 }

   	SubscriberWSGetAlternateIdSeq ::= SEQUENCE {
   	       getAlternateIdResultCode  			Counter32,
   	       getAlternateIdResultCodeName  		SnmpAdminString,
   	       getAlternateIdResultCodeCounters  	Counter32
   	}

   	subscriberWSGetAlternateIdEntry OBJECT-TYPE
   	       SYNTAX     SubscriberWSGetAlternateIdSeq
   	       MAX-ACCESS not-accessible
   	       STATUS     current
   	       DESCRIPTION
   	             "An entry (conceptual row) representing a SubscriberProvisioningWS Method wsGetAlternateId ResultCode specific statistics."

   	       INDEX      { getAlternateIdResultCode }
   	       ::= { subscriberProvisioningWSGetAlternateIdTable 1 }

   	getAlternateIdResultCode OBJECT-TYPE
   	       SYNTAX     Integer32 (1..2147483647)
   	       MAX-ACCESS not-accessible
   	       STATUS     current
   	       DESCRIPTION
   	             "SubscriberProvisioningWS method wsGetAlternateId ResultCode."
   	       ::= { subscriberWSGetAlternateIdEntry 1 }

   	getAlternateIdResultCodeName OBJECT-TYPE
   	    SYNTAX SnmpAdminString
   	    MAX-ACCESS read-only
   	    STATUS current
   	    DESCRIPTION
   	         "SubscriberProvisioningWS method wsGetAlternateId ResultCode Name."
   	    ::= { subscriberWSGetAlternateIdEntry 2 }

   	getAlternateIdResultCodeCounters OBJECT-TYPE
   	    SYNTAX Counter32
   	    MAX-ACCESS read-only
   	    STATUS current
   	    DESCRIPTION
   	         "SubscriberProvisioningWS method wsGetAlternateId ResultCode Specific statistics."
   	    ::= { subscriberWSGetAlternateIdEntry 3 }

      -- SUBSCRIBER-PROVISIONING-WS METHOD wsGetAlternateId END --

-- SUBSCRIBER-PROVISIONING-WS METHOD WISE RESULT CODE END --         
	
-- END OF SubscriberProvisioningWS 

-- SessionManagementWS BEGIN
	
sessionManagementWSStatistics OBJECT IDENTIFIER ::= { netvertexWebServiceStatistics 11 }

sessionWSTotalRequests OBJECT-TYPE
    SYNTAX Counter32
    MAX-ACCESS read-only
    STATUS current
    DESCRIPTION
         "Total number of SessionManagementWS requests received by Policy Designer."
    ::= { sessionManagementWSStatistics 1 }

sessionWSTotalResponses OBJECT-TYPE
    SYNTAX Counter32
    MAX-ACCESS read-only
    STATUS current
    DESCRIPTION
         "Total number of SessionManagementWS responses given by Policy Designer."
    ::= { sessionManagementWSStatistics 2 }

sessionWSLastMinuteTotalRequests OBJECT-TYPE
    SYNTAX Counter32
    MAX-ACCESS read-only
    STATUS current
    DESCRIPTION
         "Total number of SessionManagementWS requests received in Last Minute by Policy Designer."
    ::= { sessionManagementWSStatistics 3 }

sessionWSAvgTPS OBJECT-TYPE
    SYNTAX Counter32
    MAX-ACCESS read-only
    STATUS current
    DESCRIPTION
         "The average TPS in SessionManagementWS for last one minute."
    ::= { sessionManagementWSStatistics 4 }
		
sessionManagementWSMethodWiseStatisticsTable OBJECT-TYPE
       SYNTAX     SEQUENCE OF SessionManagementWSMethodWiseSeq
       MAX-ACCESS not-accessible
       STATUS     current
       DESCRIPTION
             "The (conceptual) table listing the SessionManagementWS method wise statistics."
       ::= { sessionManagementWSStatistics 5 }
       
SessionManagementWSMethodWiseSeq ::= SEQUENCE {
       sessionWSMethodIndex   		Integer32,
       sessionWSMethodName     		SnmpAdminString,
       sessionWSMethodTotalRequests      		Counter32,
       sessionWSMethodTotalResponses         	Counter32,
       sessionWSMethodLastMinuteTotalRequests	Counter32,
       sessionWSMethodAvgTPS                 	Counter32
 }       
	
sessionManagementWSMethodWiseEntry OBJECT-TYPE
       SYNTAX     SessionManagementWSMethodWiseSeq
       MAX-ACCESS not-accessible
       STATUS     current
       DESCRIPTION
             "An entry (conceptual row) representing a SessionManagementWS
              method wise statistics."

       INDEX      { sessionWSMethodIndex }
       ::= { sessionManagementWSMethodWiseStatisticsTable 1 }
       
sessionWSMethodIndex OBJECT-TYPE
       SYNTAX     Integer32 (1..2147483647)
       MAX-ACCESS not-accessible
       STATUS     current
       DESCRIPTION
             " SessionManagementWS method's Index"
       ::= { sessionManagementWSMethodWiseEntry 1 }
   
sessionWSMethodName OBJECT-TYPE
       SYNTAX     SnmpAdminString
       MAX-ACCESS read-only
       STATUS     current
       DESCRIPTION
             "SessionManagementWS method's Name"
       ::= { sessionManagementWSMethodWiseEntry 2 }
       
sessionWSMethodTotalRequests OBJECT-TYPE
    SYNTAX Counter32
    MAX-ACCESS read-only
    STATUS current
    DESCRIPTION
         "Total number of SessionManagementWS method wise Requests received by Policy Designer."
    ::= { sessionManagementWSMethodWiseEntry 3 }

sessionWSMethodTotalResponses OBJECT-TYPE
    SYNTAX Counter32
    MAX-ACCESS read-only
    STATUS current
    DESCRIPTION
         "Total number of SessionManagementWS method wise Responses given by Policy Designer."
    ::= { sessionManagementWSMethodWiseEntry 4 }

sessionWSMethodLastMinuteTotalRequests OBJECT-TYPE
    SYNTAX Counter32
    MAX-ACCESS read-only
    STATUS current
    DESCRIPTION
         "Total number of SessionManagementWS method wise Requests received in Last Minute by Policy Designer."
    ::= { sessionManagementWSMethodWiseEntry 5 }

sessionWSMethodAvgTPS OBJECT-TYPE
    SYNTAX Counter32
    MAX-ACCESS read-only
    STATUS current
    DESCRIPTION
         "Method's average TPS in SessionManagementWS for last one minute."
    ::= { sessionManagementWSMethodWiseEntry 6 }
       
	
-- SESSION-MANAGEMENT-WS RESULT CODE STATISTICS BEGIN --
       
sessionManagementWSResultCodeWiseStatisticsTable OBJECT-TYPE
       SYNTAX     SEQUENCE OF SessionWSResultCodeWiseSeq
       MAX-ACCESS not-accessible
       STATUS     current
       DESCRIPTION
             "The (conceptual) table listing the SessionManagementWS ResultCodes statistics."
       ::= { sessionManagementWSStatistics 6 }
       
SessionWSResultCodeWiseSeq ::= SEQUENCE {             
       sessionWSResultCode  			Counter32,
       sessionWSResultCodeName  		SnmpAdminString,
       sessionWSResultCodeCounters  	Counter32       
}       
	
sessionWSResultCodeWiseEntry OBJECT-TYPE
       SYNTAX     SessionWSResultCodeWiseSeq
       MAX-ACCESS not-accessible
       STATUS     current
       DESCRIPTION
             "An entry (conceptual row) representing a SessionManagementWS ResultCode specific statistics."

       INDEX      { sessionWSResultCode }
       ::= { sessionManagementWSResultCodeWiseStatisticsTable 1 }   
       
sessionWSResultCode OBJECT-TYPE
       SYNTAX     Integer32 (1..2147483647)
       MAX-ACCESS not-accessible
       STATUS     current
       DESCRIPTION
             "SessionManagementWS ResultCode."
       ::= { sessionWSResultCodeWiseEntry 1 }       
   
sessionWSResultCodeName OBJECT-TYPE
    SYNTAX SnmpAdminString
    MAX-ACCESS read-only
    STATUS current
    DESCRIPTION
         "SessionManagementWS ResultCode Name."
    ::= { sessionWSResultCodeWiseEntry 2 }

sessionWSResultCodeCounters OBJECT-TYPE
    SYNTAX Counter32
    MAX-ACCESS read-only
    STATUS current
    DESCRIPTION
         "SessionManagementWS ResultCode statistics."
    ::= { sessionWSResultCodeWiseEntry 3 }
    
-- SESSION-MANAGEMENT-WS RESULT CODE STATISTICS END --
   
-- SESSION-MANAGEMENT-WS METHOD WISE RESULT CODE BEGIN --

	-- SESSION-MANAGEMENT-WS METHOD1 wsGetSessionsBySubscriberIdentity BEGIN --
	
	sessionManagementWSGetSessionsBySubscriberIDTable OBJECT-TYPE
	       SYNTAX     SEQUENCE OF SessionWSGetSessionsBySubscriberIDSeq
	       MAX-ACCESS not-accessible
	       STATUS     current
	       DESCRIPTION
	             "The (conceptual) table listing the SessionManagementWS Method wsGetSessionsBySubscriberIdentity ResultCodes statistics."
	       ::= { sessionManagementWSStatistics 7 }
	       
	SessionWSGetSessionsBySubscriberIDSeq ::= SEQUENCE {		                  
	       getSessionsBySubscriberIDResultCode  			Counter32,
	       getSessionsBySubscriberIDResultCodeName  		SnmpAdminString,
	       getSessionsBySubscriberIDResultCodeCounters  	Counter32       
	}       
		
	sessionWSGetSessionsBySubscriberIDEntry OBJECT-TYPE
	       SYNTAX     SessionWSGetSessionsBySubscriberIDSeq
	       MAX-ACCESS not-accessible
	       STATUS     current
	       DESCRIPTION
	             "An entry (conceptual row) representing a SessionManagementWS Method wsGetSessionsBySubscriberIdentity ResultCode specific statistics."
	
	       INDEX      { getSessionsBySubscriberIDResultCode }
	       ::= { sessionManagementWSGetSessionsBySubscriberIDTable 1 }   
	       
	getSessionsBySubscriberIDResultCode OBJECT-TYPE
	       SYNTAX     Integer32 (1..2147483647)
	       MAX-ACCESS not-accessible
	       STATUS     current
	       DESCRIPTION
	             "SessionManagementWS method wsGetSessionsBySubscriberID ResultCode."
	       ::= { sessionWSGetSessionsBySubscriberIDEntry 1 }       
	   
	getSessionsBySubscriberIDResultCodeName OBJECT-TYPE
	    SYNTAX SnmpAdminString
	    MAX-ACCESS read-only
	    STATUS current
	    DESCRIPTION
	         "SessionManagementWS method wsGetSessionsBySubscriberIdentity ResultCode Name."
	    ::= { sessionWSGetSessionsBySubscriberIDEntry 2 }
	
	getSessionsBySubscriberIDResultCodeCounters OBJECT-TYPE
	    SYNTAX Counter32
	    MAX-ACCESS read-only
	    STATUS current
	    DESCRIPTION
	         "SessionManagementWS method wsGetSessionsBySubscriberIdentity ResultCode Specific statistics."
	    ::= { sessionWSGetSessionsBySubscriberIDEntry 3 }
	    
	-- SESSION-MANAGEMENT-WS METHOD1 wsGetSessionsBySubscriberIdentity END --
    
	-- SESSION-MANAGEMENT-WS METHOD2 wsGetSessionsByIP BEGIN --
	
	sessionManagementWSGetSessionsByIPTable OBJECT-TYPE
	       SYNTAX     SEQUENCE OF SessionWSGetSessionsByIPSeq
	       MAX-ACCESS not-accessible
	       STATUS     current
	       DESCRIPTION
	             "The (conceptual) table listing the SessionManagementWS Method wsGetSessionsByIP ResultCodes statistics."
	       ::= { sessionManagementWSStatistics 8 }
	       
	SessionWSGetSessionsByIPSeq ::= SEQUENCE {		                  
	       getSessionsByIPResultCode  			Counter32,
	       getSessionsByIPResultCodeName  		SnmpAdminString,
	       getSessionsByIPResultCodeCounters  	Counter32       
	}       
		
	sessionWSGetSessionsByIPEntry OBJECT-TYPE
	       SYNTAX     SessionWSGetSessionsByIPSeq
	       MAX-ACCESS not-accessible
	       STATUS     current
	       DESCRIPTION
	             "An entry (conceptual row) representing a SessionManagementWS Method wsGetSessionsByIP ResultCode specific statistics."
	
	       INDEX      { getSessionsByIPResultCode }
	       ::= { sessionManagementWSGetSessionsByIPTable 1 }   
	       
	getSessionsByIPResultCode OBJECT-TYPE
	       SYNTAX     Integer32 (1..2147483647)
	       MAX-ACCESS not-accessible
	       STATUS     current
	       DESCRIPTION
	             "SessionManagementWS method wsGetSessionsByIP ResultCode."
	       ::= { sessionWSGetSessionsByIPEntry 1 }       
	   
	getSessionsByIPResultCodeName OBJECT-TYPE
	    SYNTAX SnmpAdminString
	    MAX-ACCESS read-only
	    STATUS current
	    DESCRIPTION
	         "SessionManagementWS method wsGetSessionsByIP ResultCode Name."
	    ::= { sessionWSGetSessionsByIPEntry 2 }
	
	getSessionsByIPResultCodeCounters OBJECT-TYPE
	    SYNTAX Counter32
	    MAX-ACCESS read-only
	    STATUS current
	    DESCRIPTION
	         "SessionManagementWS method wsGetSessionsByIP ResultCode Specific statistics."
	    ::= { sessionWSGetSessionsByIPEntry 3 }
	    
	-- SESSION-MANAGEMENT-WS METHOD2 wsGetSessionsByIP END --
    
	-- SESSION-MANAGEMENT-WS METHOD3 wsReauthSessionsBySubscriberIdentity BEGIN --
	
	sessionManagementWSReauthSessionBySubscriberIDTable OBJECT-TYPE
	       SYNTAX     SEQUENCE OF SessionWSReauthSessionBySubscriberIDSeq
	       MAX-ACCESS not-accessible
	       STATUS     current
	       DESCRIPTION
	             "The (conceptual) table listing the SessionManagementWS Method wsReauthSessionsBySubscriberIdentity ResultCodes statistics."
	       ::= { sessionManagementWSStatistics 9 }
	       
	SessionWSReauthSessionBySubscriberIDSeq ::= SEQUENCE {		                  
	       reauthSessionBySubscriberIDResultCode  			Counter32,
	       reauthSessionBySubscriberIDResultCodeName  		SnmpAdminString,
	       reauthSessionBySubscriberIDResultCodeCounters  	Counter32       
	}       
		
	sessionWSReauthSessionBySubscriberIDEntry OBJECT-TYPE
	       SYNTAX     SessionWSReauthSessionBySubscriberIDSeq
	       MAX-ACCESS not-accessible
	       STATUS     current
	       DESCRIPTION
	             "An entry (conceptual row) representing a SessionManagementWS Method wsReauthSessionsBySubscriberIdentity ResultCode specific statistics."
	
	       INDEX      { reauthSessionBySubscriberIDResultCode }
	       ::= { sessionManagementWSReauthSessionBySubscriberIDTable 1 }   
	       
	reauthSessionBySubscriberIDResultCode OBJECT-TYPE
	       SYNTAX     Integer32 (1..2147483647)
	       MAX-ACCESS not-accessible
	       STATUS     current
	       DESCRIPTION
	             "SessionManagementWS method wsReauthSessionsBySubscriberIdentity ResultCode."
	       ::= { sessionWSReauthSessionBySubscriberIDEntry 1 }       
	   
	reauthSessionBySubscriberIDResultCodeName OBJECT-TYPE
	    SYNTAX SnmpAdminString
	    MAX-ACCESS read-only
	    STATUS current
	    DESCRIPTION
	         "SessionManagementWS method wsReauthSessionsBySubscriberIdentity ResultCode Name."
	    ::= { sessionWSReauthSessionBySubscriberIDEntry 2 }
	
	reauthSessionBySubscriberIDResultCodeCounters OBJECT-TYPE
	    SYNTAX Counter32
	    MAX-ACCESS read-only
	    STATUS current
	    DESCRIPTION
	         "SessionManagementWS method wsReauthSessionsBySubscriberIdentity ResultCode Specific statistics."
	    ::= { sessionWSReauthSessionBySubscriberIDEntry 3 }
	    
	-- SESSION-MANAGEMENT-WS METHOD3 wsReauthSessionsBySubscriberIdentity END --
    
	-- SESSION-MANAGEMENT-WS METHOD4 wsReauthSessionsByCoreSessionId BEGIN --
	
	sessionManagementWSReauthSessionsByCoreSessionIDTable OBJECT-TYPE
	       SYNTAX     SEQUENCE OF SessionWSReauthSessionsByCoreSessionIDSeq
	       MAX-ACCESS not-accessible
	       STATUS     current
	       DESCRIPTION
	             "The (conceptual) table listing the SessionManagementWS Method wsReauthSessionsByCoreSessionId ResultCodes statistics."
	       ::= { sessionManagementWSStatistics 10 }
	       
	SessionWSReauthSessionsByCoreSessionIDSeq ::= SEQUENCE {		                  
	       reauthSessionsByCoreSessionIDResultCode  			Counter32,
	       reauthSessionsByCoreSessionIDResultCodeName  		SnmpAdminString,
	       reauthSessionsByCoreSessionIDResultCodeCounters  	Counter32       
	}       
		
	sessionWSReauthSessionsByCoreSessionIDEntry OBJECT-TYPE
	       SYNTAX     SessionWSReauthSessionsByCoreSessionIDSeq
	       MAX-ACCESS not-accessible
	       STATUS     current
	       DESCRIPTION
	             "An entry (conceptual row) representing a SessionManagementWS Method wsReauthSessionsByCoreSessionId ResultCode specific statistics."
	
	       INDEX      { reauthSessionsByCoreSessionIDResultCode }
	       ::= { sessionManagementWSReauthSessionsByCoreSessionIDTable 1 }   
	       
	reauthSessionsByCoreSessionIDResultCode OBJECT-TYPE
	       SYNTAX     Integer32 (1..2147483647)
	       MAX-ACCESS not-accessible
	       STATUS     current
	       DESCRIPTION
	             "SessionManagementWS method wsReauthSessionsByCoreSessionId ResultCode."
	       ::= { sessionWSReauthSessionsByCoreSessionIDEntry 1 }       
	   
	reauthSessionsByCoreSessionIDResultCodeName OBJECT-TYPE
	    SYNTAX SnmpAdminString
	    MAX-ACCESS read-only
	    STATUS current
	    DESCRIPTION
	         "SessionManagementWS method wsReauthSessionsByCoreSessionId ResultCode Name."
	    ::= { sessionWSReauthSessionsByCoreSessionIDEntry 2 }
	
	reauthSessionsByCoreSessionIDResultCodeCounters OBJECT-TYPE
	    SYNTAX Counter32
	    MAX-ACCESS read-only
	    STATUS current
	    DESCRIPTION
	         "SessionManagementWS method wsReauthSessionsByCoreSessionId ResultCode Specific statistics."
	    ::= { sessionWSReauthSessionsByCoreSessionIDEntry 3 }
	    
	-- SESSION-MANAGEMENT-WS METHOD4 wsReauthSessionsByCoreSessionId END --
    
-- SESSION-MANAGEMENT-WS METHOD WISE RESULT CODE END --
  	
-- END OF SessionManagementWS --

	
-- ResetUsageWS BEGIN
	
resetUsageWSStatistics OBJECT IDENTIFIER ::= { netvertexWebServiceStatistics 12 }

resetUsageWSTotalRequests OBJECT-TYPE
    SYNTAX Counter32
    MAX-ACCESS read-only
    STATUS current
    DESCRIPTION
         "Total number of ResetUsageWS requests received by Policy Designer."
    ::= { resetUsageWSStatistics 1 }

resetUsageWSTotalResponses OBJECT-TYPE
    SYNTAX Counter32
    MAX-ACCESS read-only
    STATUS current
    DESCRIPTION
         "Total number of ResetUsageWS responses given by Policy Designer."
    ::= { resetUsageWSStatistics 2 }

resetUsageWSLastMinuteTotalRequests OBJECT-TYPE
    SYNTAX Counter32
    MAX-ACCESS read-only
    STATUS current
    DESCRIPTION
         "Total number of ResetUsageWS requests received in Last Minute by Policy Designer."
    ::= { resetUsageWSStatistics 3 }

resetUsageWSAvgTPS OBJECT-TYPE
    SYNTAX Counter32
    MAX-ACCESS read-only
    STATUS current
    DESCRIPTION
         "The average TPS in ResetUsageWS for last one minute."
    ::= { resetUsageWSStatistics 4 }
		
resetUsageWSMethodWiseStatisticsTable OBJECT-TYPE
       SYNTAX     SEQUENCE OF ResetUsageWSMethodWiseSeq
       MAX-ACCESS not-accessible
       STATUS     current
       DESCRIPTION
             "The (conceptual) table listing the ResetUsageWS methods specific statistics."
       ::= { resetUsageWSStatistics 5 }
       
ResetUsageWSMethodWiseSeq ::= SEQUENCE {
       resetUsageWSMethodIndex   		Integer32,
       resetUsageWSMethodName     		SnmpAdminString,
       resetUsageWSMethodTotalRequests      		Counter32,
       resetUsageWSMethodTotalResponses         	Counter32,
       resetUsageWSMethodLastMinuteTotalRequests	Counter32,
       resetUsageWSMethodAvgTPS                 	Counter32
 }       
	
resetUsageWSMethodWiseEntry OBJECT-TYPE
       SYNTAX     ResetUsageWSMethodWiseSeq
       MAX-ACCESS not-accessible
       STATUS     current
       DESCRIPTION
             "An entry (conceptual row) representing a ResetUsageWS
              method specific statistics."

       INDEX      { resetUsageWSMethodIndex }
       ::= { resetUsageWSMethodWiseStatisticsTable 1 }
       
resetUsageWSMethodIndex OBJECT-TYPE
       SYNTAX     Integer32 (1..2147483647)
       MAX-ACCESS not-accessible
       STATUS     current
       DESCRIPTION
             "ResetUsageWS mMethod's Index."
       ::= { resetUsageWSMethodWiseEntry 1 }
   
resetUsageWSMethodName OBJECT-TYPE
       SYNTAX     SnmpAdminString
       MAX-ACCESS read-only
       STATUS     current
       DESCRIPTION
             "ResetUsageWS method's Name."
       ::= { resetUsageWSMethodWiseEntry 2 }
       
resetUsageWSMethodTotalRequests OBJECT-TYPE
    SYNTAX Counter32
    MAX-ACCESS read-only
    STATUS current
    DESCRIPTION
         "Total number of ResetUsageWS method wise Requests received by Policy Designer."
    ::= { resetUsageWSMethodWiseEntry 3 }

resetUsageWSMethodTotalResponses OBJECT-TYPE
    SYNTAX Counter32
    MAX-ACCESS read-only
    STATUS current
    DESCRIPTION
         "Total number of ResetUsageWS method wise Responses given by Policy Designer."
    ::= { resetUsageWSMethodWiseEntry 4 }

resetUsageWSMethodLastMinuteTotalRequests OBJECT-TYPE
    SYNTAX Counter32
    MAX-ACCESS read-only
    STATUS current
    DESCRIPTION
         "Total number of ResetUsageWS method wise Requests received in Last Minute by Policy Designer."
    ::= { resetUsageWSMethodWiseEntry 5 }

resetUsageWSMethodAvgTPS OBJECT-TYPE
    SYNTAX Counter32
    MAX-ACCESS read-only
    STATUS current
    DESCRIPTION
         "Method's average TPS in ResetUsageWS for last one minute."
    ::= { resetUsageWSMethodWiseEntry 6 }
       	
       	
-- RESET-USAGE-WS RESULT CODE STATISTICS BEGIN --
       
resetUsageWSResultCodeWiseStatisticsTable OBJECT-TYPE
       SYNTAX     SEQUENCE OF ResetUsageWSResultCodeWiseSeq
       MAX-ACCESS not-accessible
       STATUS     current
       DESCRIPTION
             "The (conceptual) table listing the ResetUsageWS ResultCodes statistics."
       ::= { resetUsageWSStatistics 6 }
       
ResetUsageWSResultCodeWiseSeq ::= SEQUENCE {             
       resetUsageWSResultCode  			Counter32,
       resetUsageWSResultCodeName  		SnmpAdminString,
       resetUsageWSResultCodeCounters  	Counter32       
}       
	
resetUsageWSResultCodeWiseEntry OBJECT-TYPE
       SYNTAX     ResetUsageWSResultCodeWiseSeq
       MAX-ACCESS not-accessible
       STATUS     current
       DESCRIPTION
             "An entry (conceptual row) representing a ResetUsageWS ResultCode specific statistics."

       INDEX      { resetUsageWSResultCode }
       ::= { resetUsageWSResultCodeWiseStatisticsTable 1 }   
       
resetUsageWSResultCode OBJECT-TYPE
       SYNTAX     Integer32 (1..2147483647)
       MAX-ACCESS not-accessible
       STATUS     current
       DESCRIPTION
             "ResetUsageWS ResultCode."
       ::= { resetUsageWSResultCodeWiseEntry 1 }       
   
resetUsageWSResultCodeName OBJECT-TYPE
    SYNTAX SnmpAdminString
    MAX-ACCESS read-only
    STATUS current
    DESCRIPTION
         "ResetUsageWS ResultCode Name."
    ::= { resetUsageWSResultCodeWiseEntry 2 }

resetUsageWSResultCodeCounters OBJECT-TYPE
    SYNTAX Counter32
    MAX-ACCESS read-only
    STATUS current
    DESCRIPTION
         "ResetUsageWS ResultCode statistics."
    ::= { resetUsageWSResultCodeWiseEntry 3 }
    
-- RESET-USAGE-WS RESULT CODE STATISTICS END --
   
-- RESET-USAGE-WS METHOD WISE RESULT CODE BEGIN --

	-- RESET-USAGE-WS METHOD1 wsResetBillingCycle BEGIN --
	
	resetUsageWSResetBillingCycleTable OBJECT-TYPE
	       SYNTAX     SEQUENCE OF ResetUsageWSResetBillingCycleSeq
	       MAX-ACCESS not-accessible
	       STATUS     current
	       DESCRIPTION
	             "The (conceptual) table listing the ResetUsageWS wsResetBillingCycle ResultCodes statistics."
	       ::= { resetUsageWSStatistics 7 }
	       
	ResetUsageWSResetBillingCycleSeq ::= SEQUENCE {		                  
	       resetUsageWSResetBillingCycleResultCode  			Counter32,
	       resetUsageWSResetBillingCycleResultCodeName  		SnmpAdminString,
	       resetUsageWSResetBillingCycleResultCodeCounters  	Counter32       
	}       
		
	resetUsageWSResetBillingCycleResultCodeEntry OBJECT-TYPE
	       SYNTAX     ResetUsageWSResetBillingCycleSeq
	       MAX-ACCESS not-accessible
	       STATUS     current
	       DESCRIPTION
	             "An entry (conceptual row) representing a ResetUsageWS wsResetBillingCycle ResultCode specific statistics."
	
	       INDEX      { resetUsageWSResetBillingCycleResultCode }
	       ::= { resetUsageWSResetBillingCycleTable 1 }   
	       
	resetUsageWSResetBillingCycleResultCode OBJECT-TYPE
	       SYNTAX     Integer32 (1..2147483647)
	       MAX-ACCESS not-accessible
	       STATUS     current
	       DESCRIPTION
	             "ResetUsageWS method wsResetBillingCycle ResultCode."
	       ::= { resetUsageWSResetBillingCycleResultCodeEntry 1 }       
	   
	resetUsageWSResetBillingCycleResultCodeName OBJECT-TYPE
	    SYNTAX SnmpAdminString
	    MAX-ACCESS read-only
	    STATUS current
	    DESCRIPTION
	         "ResetUsageWS method wsResetBillingCycle ResultCode Name."
	    ::= { resetUsageWSResetBillingCycleResultCodeEntry 2 }
	
	resetUsageWSResetBillingCycleResultCodeCounters OBJECT-TYPE
	    SYNTAX Counter32
	    MAX-ACCESS read-only
	    STATUS current
	    DESCRIPTION
	         "ResetUsageWS method wsResetBillingCycle ResultCode Specific statistics."
	    ::= { resetUsageWSResetBillingCycleResultCodeEntry 3 }
    
    -- RESET-USAGE-WS METHOD1 wsResetBillingCycle END --
    
-- RESET-USAGE-WS METHOD WISE RESULT CODE END --         	
-- END OF ResetUsageWS --
 	
END
