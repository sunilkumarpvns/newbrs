DIAMETER-BASE-PROTOCOL-MIB DEFINITIONS ::= BEGIN

IMPORTS
      InetAddressType,
      InetAddress
            FROM INET-ADDRESS-MIB -- [RFC4001]
      MODULE-IDENTITY,
      OBJECT-TYPE,
      NOTIFICATION-TYPE,
      Integer32,
      Counter32,
      Unsigned32,
      Gauge32,
      TimeTicks
            FROM SNMPv2-SMI -- [RFC2578]
      SnmpAdminString
            FROM SNMP-FRAMEWORK-MIB -- [RFC3411]
      NOTIFICATION-GROUP,
      MODULE-COMPLIANCE,
      OBJECT-GROUP
            FROM SNMPv2-CONF -- [RFC2580]
      RowStatus,
      TruthValue,
      StorageType
            FROM SNMPv2-TC -- [RFC2579]
      mib-2
	FROM SNMPv2-SMI; -- [RFC2578]


diameterBaseProtocolMIB MODULE-IDENTITY
      LAST-UPDATED "201105040000Z" -- 4 May 2011
      ORGANIZATION "IETF dime Working Group."
      CONTACT-INFO
          "Glen Zorn
           Network Zen
           227/358 Thanon Sanphawut
           Bang Na, Bangkok 10260
           Thailand
           Email: gwz@net-zen.net"
       DESCRIPTION
           "The MIB module for entities implementing the
           Diameter Base Protocol.

           Copyright (c) 2011 IETF Trust and the persons identified
           as the document authors.  All rights reserved.

           The initial version of this MIB module was published
           in RFC yyyy; for full legal notices see the RFC itself.
           Supplementary information may be available on
           http://www.ietf.org/copyrights/ianamib.html."

-- RFC Ed.: replace yyyy with actual RFC number and remove this note

      REVISION "201105040000Z" -- 4 May 2011
      DESCRIPTION "Initial version as published in RFC yyyy"
-- RFC Ed.: replace yyyy with actual RFC number and remove this note
      ::= { mib-2 119 }  -- Experimental value assigned by IANA.

-- Top-Level Components of this MIB.

diameterBaseNotifications  OBJECT IDENTIFIER ::=
                                     { diameterBaseProtocolMIB 0 }
diameterBaseObjects        OBJECT IDENTIFIER ::=

                                     { diameterBaseProtocolMIB 1 }
diameterBaseConform        OBJECT IDENTIFIER ::=
                                     { diameterBaseProtocolMIB 2 }

dbpLocalCfgs    OBJECT IDENTIFIER ::= { diameterBaseObjects 1 }
dbpLocalStats   OBJECT IDENTIFIER ::= { diameterBaseObjects 2 }
dbpPeerCfgs     OBJECT IDENTIFIER ::= { diameterBaseObjects 3 }
dbpPeerStats    OBJECT IDENTIFIER ::= { diameterBaseObjects 4 }
dbpRealmCfgs    OBJECT IDENTIFIER ::= { diameterBaseObjects 5 }
dbpRealmStats   OBJECT IDENTIFIER ::= { diameterBaseObjects 6 }
dbpNotifCfgs    OBJECT IDENTIFIER ::= { diameterBaseObjects 7 }
eliteDSC    OBJECT IDENTIFIER ::= { diameterBaseObjects 11 }


-- Textual Conventions

ServiceType ::= TEXTUAL-CONVENTION
    DISPLAY-HINT  "d"
    STATUS        current
    DESCRIPTION
          "An enumerated value which provides an indication of the
          type of services supported for each Diameter application:
          accounting, authentication or both."

     SYNTAX        INTEGER { acct(1),
                             auth(2),
                             both(3) }


-- Protocol Error Notifications

dbpProtocolErrorNotifEnabled OBJECT-TYPE
       SYNTAX      TruthValue
       MAX-ACCESS  read-write
       STATUS      current
       DESCRIPTION
             "Setting the value of this object to True(1)
              enables the dbpProtocolErrorNotif notification.
              The value persists across resets."
       DEFVAL      {false}
       ::= { dbpNotifCfgs 1 }

dbpProtocolErrorNotif NOTIFICATION-TYPE
       OBJECTS {
                  dbpPeerId,
                  dbpPerPeerStatsProtocolErrors
               }

       STATUS     current
       DESCRIPTION
             "An dbpProtocolError Notification is sent when both the
              following conditions are true:
              1) the value of dbpProtocolErrorNotifEnabled is True(1)
              2) the value of dbpPerPeerStatsProtocolErrors changes
              An agent must not generate more than one
              dbpProtocolError 'notification event' in a five second
              period, where a 'notification event' is the
              transmission of a single Notification PDU to a list of
              Notification destinations.
              If additional protocol errors occur within the
              five second 'throttling' period, then these
              notification events should be suppressed by the agent.
              An NMS should periodically check the value of
              dbpPerPeerStatsProtocolErrors to detect any missed
              dbpProtocolError notification events, e.g. due to
              throttling or transmission loss."
      ::= { diameterBaseNotifications 1 }


-- Transient Error Notifications

dbpTransientFailureNotifEnabled OBJECT-TYPE
       SYNTAX      TruthValue
       MAX-ACCESS  read-write
       STATUS      current
       DESCRIPTION
             "Setting the value of this object to True(1)
              enables the dbpTransientFailure Notification.
              The value persists across resets."
       ::= { dbpNotifCfgs 2 }

dbpTransientFailureNotif NOTIFICATION-TYPE
       OBJECTS  {
                   dbpPeerId,
                   dbpPerPeerStatsTransientFailures
                }
       STATUS     current
       DESCRIPTION
             "An dbpTransientFailure Notification is sent when both
              the following conditions are true:
              1) the value of dbpTransientFailureNotifEnabled
                 is True(1)
              2) the value of dbpPerPeerStatsTransientFailures
                 changes
              An agent must not generate more than one
              dbpTransientFailure 'notification event' in a five
              second period, where a 'notification event' is the
              transmission of a single notification PDU to a list
              of notification destinations.
              If additional transient failures occur
              within the five second 'throttling' period, then
              these notification events should be suppressed
              by the agent.
              An NMS should periodically check the value of
              dbpPerPeerStatsTransientFailures to detect any
              missed dbpTransientFailure notification events,
              e.g. due to throttling or transmission loss."
      ::= { diameterBaseNotifications 2 }


-- Permanent Failure Notifications

dbpPermanentFailureNotifEnabled OBJECT-TYPE
       SYNTAX      TruthValue
       MAX-ACCESS  read-write
       STATUS      current
       DESCRIPTION
             "Setting the value of this object to True(1)
              enables the dbpPermanentFailure notification.
              The value persists across resets."
       DEFVAL    { false }
       ::= { dbpNotifCfgs 3 }

dbpPermanentFailureNotif NOTIFICATION-TYPE
       OBJECTS  {
                   dbpPeerId,
                   dbpPerPeerStatsPermanentFailures
                }
       STATUS     current
       DESCRIPTION
             "An dbpPermanentFailure notification is sent when
              both the following conditions are true:
              1) the value of dbpPermanentFailureNotifEnabled
                 is True(1)
              2) the value of dbpPerPeerStatsPermanentFailures
                 changes
              An agent must not generate more than one
              dbpPermanentFailure 'notification event' in a five
              second period, where a 'notification event' is the
              transmission of a single notification PDU to a list
              of notification destinations.
              If additional permanent failures occur within the
              five second 'throttling' period, then these
              trap-events should be suppressed by the agent.
              An NMS should periodically check the value of
              dbpPerPeerStatsPermanentFailures to detect
              any missed dbpPermanentFailure trap-events,
              e.g. due to throttling or transmission loss."
      ::= { diameterBaseNotifications 3 }


-- Connection Down Notifs

dbpPeerConnectionDownNotifEnabled OBJECT-TYPE
       SYNTAX      TruthValue
       MAX-ACCESS  read-write
       STATUS      current
       DESCRIPTION
             "Setting the value of this object to True(1)
              enables the dbpPeerConnectionDown notification.
              The value persists across resets."
       DEFVAL      { false }
       ::= { dbpNotifCfgs 4 }

dbpPeerConnectionDownNotif NOTIFICATION-TYPE
       OBJECTS  {
                   dbpLocalId,
                   dbpPeerId
                }
       STATUS     current
       DESCRIPTION
             "An dbpPeerConnectionDown notification is sent when
              both the following conditions are true:
              1) the value of dbpPeerConnectionDownNotifEnabled is
                 True(1)
              2) dbpPerPeerStatsState changes to closed(1)
              An agent must not generate more than one
              dbpPeerConnectionDown
              'notification event' in a five second period, where a
              'notification event' is the transmission of a single
              notification PDU to a list of notification
              destinations.
              If additional 'transport down' events occur within the
              five second 'throttling' period, then these trap-events
              should be suppressed by the agent."
      ::= { diameterBaseNotifications 4 }


-- Connection Up Notifications

dbpPeerConnectionUpNotifEnabled OBJECT-TYPE
       SYNTAX      TruthValue
       MAX-ACCESS  read-write
       STATUS      current
       DESCRIPTION
             "Setting the value of this object to True(1)
              enables the dbpPeerConnectionUp notification.
              The value persists across resets."
       DEFVAL      { false }
       ::= { dbpNotifCfgs 5 }
	   
-- Elite DSC Group

totalActiveSession OBJECT-TYPE
       SYNTAX      Counter32
       MAX-ACCESS  read-only
       STATUS      current
       DESCRIPTION
             "The total number of active diameter sessions."
       ::= { eliteDSC 1 }
	   
totalActiveRoutingSession OBJECT-TYPE
       SYNTAX      Counter32
       MAX-ACCESS  read-only
       STATUS      current
       DESCRIPTION
             "The total number of active diameter routing sessions."
       ::= { eliteDSC 2 }
	 
avgRoundTripTime OBJECT-TYPE
       SYNTAX      Counter32
       MAX-ACCESS  read-only
       STATUS      current
       DESCRIPTION
             "The average round trip time for last one minute."
       ::= { eliteDSC 3 }

avgIncomingMPS OBJECT-TYPE
       SYNTAX      Counter32
       MAX-ACCESS  read-only
       STATUS      current
       DESCRIPTION
             "The average incoming messages per second for last one minute."
       ::= { eliteDSC 4 }

dbpPeerConnectionUpNotif NOTIFICATION-TYPE
       OBJECTS  {
                   dbpLocalId,
                   dbpPeerId
                }
       STATUS     current
       DESCRIPTION
             "An dbpPeerConnectionUp notification is sent
              when both thefollowing conditions are true:
              1) the value of dbpPeerConnectionUpNotifEnabled is
                 True(1)
              2) the value of dbpPerPeerStatsState changes to
                 either rOpen(6)or iOpen(7)
              An agent must not generate
              more than one dbpPeerConnectionUp
              'notification event' in a
              five second period, where a 'notification event' is the
              transmission of a single notification PDU to a
              list of notification destinations.
              If additional 'connection up' events
              occur within the five second 'throttling' period,
              then these trap-events should be suppressed by the
              agent."
      ::= { diameterBaseNotifications 5 }


-- Local Configs

dbpLocalId OBJECT-TYPE
       SYNTAX     SnmpAdminString
       MAX-ACCESS read-only
       STATUS     current
       DESCRIPTION
             "The implementation-specific identification
              string for the Diameter software in use on
              the system; for example: 'diameterd'"
       ::= { dbpLocalCfgs 1 }

dbpLocalTcpListenPort OBJECT-TYPE
       SYNTAX      Unsigned32 (1..65535)
       MAX-ACCESS  read-only
       STATUS      current
       DESCRIPTION
             "Diameter TCP 'listen' port."
       ::= { dbpLocalCfgs 3 }

dbpLocalSctpListenPort OBJECT-TYPE
       SYNTAX      Unsigned32 (1..65535)
       MAX-ACCESS  read-only
       STATUS      current
       DESCRIPTION
             "Diameter SCTP 'listen' port."
       ::= { dbpLocalCfgs 4 }

dbpLocalOriginHost OBJECT-TYPE
    SYNTAX          SnmpAdminString
    MAX-ACCESS      read-write
    STATUS          current
    DESCRIPTION     "This object represents the host name of
                    the local peer.
                    The value persists across resets."
    DEFVAL          { "" }
    ::= { dbpLocalCfgs 5 }

dbpLocalRealm OBJECT-TYPE
    SYNTAX          SnmpAdminString
    MAX-ACCESS      read-write
    STATUS          current
    DESCRIPTION     "This object represents the Local Realm Name."
    DEFVAL          { "" }
    ::= { dbpLocalCfgs 6 }


dbpLocalStatsTotalMessagesIn OBJECT-TYPE
       SYNTAX      Counter32 UNITS "messages"
       MAX-ACCESS  read-only
       STATUS      current
       DESCRIPTION
             "The total number of Diameter Base Protocol
              messages received since the last reset."
       ::= { dbpLocalStats 1 }

dbpLocalStatsTotalMessagesOut OBJECT-TYPE
       SYNTAX      Counter32 UNITS "messages"
       MAX-ACCESS  read-only
       STATUS      current
       DESCRIPTION
             "The total number of Diameter Base Protocol
              messages transmitted since the last reset."
       ::= { dbpLocalStats 2 }

dbpLocalStatsTotalUpTime OBJECT-TYPE
       SYNTAX     TimeTicks
       MAX-ACCESS read-only
       STATUS     current
       DESCRIPTION
             "This object represents the total amount of
              time this Diameter peer has been up from the
              beginning of time until now.  The value is cumulative
              and persists over resets."
       ::= { dbpLocalStats 3 }

dbpLocalResetTime OBJECT-TYPE
       SYNTAX     TimeTicks
       MAX-ACCESS read-only
       STATUS     current
       DESCRIPTION
             "If the peer keeps persistent state (e.g., a process)
              and supports a 'reset' operation (e.g., can be told to
              re-read configuration files), this value will be the
              time elapsed (in hundredths of a second) since the
              peer was 'reset'.  For software that does not
              have persistence or does not support a 'reset'
              operation, this value is undefined."
       ::= { dbpLocalStats 4 }

dbpLocalConfigReset OBJECT-TYPE
       SYNTAX     INTEGER { other(1),
                            initializing(2),
                            running(3),
                            reset(4) }
       MAX-ACCESS read-write
       STATUS     current
       DESCRIPTION
             "Status/action object to reinitialize any persistent
              local state.  When set to reset(4), any persistent
              local state (such as a process) is reinitialized as
              if the software had just been started.  This value will
              never be returned by a read operation.  When read,
              one of the following values will be returned:
                 other(1) - peer in some unknown state;
                 initializing(2) - peer (re)initializing;
                 running(3) - peer currently running."
       DEFVAL      { other }
       ::= { dbpLocalStats 5 }

dbpLocalApplTable OBJECT-TYPE
       SYNTAX     SEQUENCE OF DbpLocalApplEntry
       MAX-ACCESS not-accessible
       STATUS     current
       DESCRIPTION
             "The table listing the Diameter applications
              supported by this peer."
       ::= { dbpLocalCfgs 7 }

dbpLocalApplEntry OBJECT-TYPE
       SYNTAX     DbpLocalApplEntry
       MAX-ACCESS not-accessible
       STATUS     current
       DESCRIPTION
             "A row entry representing a Diameter
              application on this peer."
       INDEX      { dbpLocalApplIndex }
       ::= { dbpLocalApplTable 1 }

DbpLocalApplEntry ::= SEQUENCE {
       dbpLocalApplIndex  Unsigned32,
       dbpLocalApplStorageType    StorageType,
       dbpLocalApplRowStatus      RowStatus
}

dbpLocalApplIndex OBJECT-TYPE
       SYNTAX      Unsigned32 ( 1..4294967295 )
       MAX-ACCESS  not-accessible
       STATUS      current
       DESCRIPTION
               "A number uniquely identifying a
               supported Diameter application. Upon reload,
               dbpLocalApplIndex values may be changed."
       ::= { dbpLocalApplEntry 1 }

dbpLocalApplStorageType OBJECT-TYPE
    SYNTAX          StorageType
    MAX-ACCESS      read-create
    STATUS          current
    DESCRIPTION
            "The storage type for this conceptual row. None of
            the columnar objects is writable when the conceptual
            row is permanent."
    REFERENCE       "Textual Conventions for SMIv2, Section 2."
    DEFVAL          { nonVolatile }
    ::= { dbpLocalApplEntry 2 }

dbpLocalApplRowStatus OBJECT-TYPE
       SYNTAX     RowStatus
       MAX-ACCESS read-create
       STATUS     current
       DESCRIPTION
            "The status of this conceptual row.

            To create a row in this table, a manager must
            set this object to either createAndGo(4) or
            createAndWait(5).

            Until instances of all corresponding columns are
            appropriately configured, the value of the
            corresponding instance of the dbpLocalApplRowStatus
            column is 'notReady'.

            In particular, a newly created row cannot be made
            active until the corresponding dbpLocalApplIndex
            has been set.

            dbpLocalApplIndex may not be modified while
            the value of this object is active(1): An attempt
            to set these objects while the value of
            dbpLocalApplRowStatus is active(1) will result in
            an inconsistentValue error.

            Entries in this table with dbpLocalApplRowStatus equal
            to active(1) remain in the table until destroyed.

            Entries in this table with dbpLocalApplRowStatus equal
            to values other than active(1) will be destroyed after
            timeout (5 minutes)."
       ::= { dbpLocalApplEntry 3 }

dbpPeerTable OBJECT-TYPE
       SYNTAX     SEQUENCE OF DbpPeerEntry
       MAX-ACCESS not-accessible
       STATUS     current
       DESCRIPTION
             "The table listing information regarding
              the discovered or configured Diameter
              peers."
       ::= { dbpPeerCfgs 1 }

dbpPeerEntry OBJECT-TYPE
       SYNTAX     DbpPeerEntry
       MAX-ACCESS not-accessible
       STATUS     current
       DESCRIPTION
             "A row entry representing a discovered
              or configured Diameter peer."
       INDEX      { dbpPeerIndex }
       ::= { dbpPeerTable 1 }

DbpPeerEntry ::= SEQUENCE {
       dbpPeerIndex                         Unsigned32,
       dbpPeerId                       SnmpAdminString,
       dbpPeerPortConnect                   Unsigned32,
       dbpPeerPortListen                    Unsigned32,
       dbpPeerTransportProtocol              Integer32,
       dbpPeerSecurity                       Integer32,
       dbpPeerFirmwareRevision         SnmpAdminString,
       dbpPeerStorageType                  StorageType,
       dbpPeerRowStatus                      RowStatus }

dbpPeerIndex OBJECT-TYPE
       SYNTAX     Unsigned32 (1..4294967295)
       MAX-ACCESS not-accessible
       STATUS     current
       DESCRIPTION
             "A number uniquely identifying each Diameter peer
              with which the local peer communicates.
              Upon reload, dbpPeerIndex values may be changed."
       ::= { dbpPeerEntry  1 }

dbpPeerId OBJECT-TYPE
       SYNTAX     SnmpAdminString
       MAX-ACCESS read-create
       STATUS     current
       DESCRIPTION
             "The local identifier for the Diameter peer.
              It must be unique and non-empty."
       ::= { dbpPeerEntry  2 }

dbpPeerPortConnect OBJECT-TYPE
       SYNTAX     Unsigned32 (0|1..65535)
       MAX-ACCESS read-only
       STATUS     current
       DESCRIPTION
             "The connection port used
              to connect to the Diameter peer.
              If there is no active connection, this
              value will be zero(0)."
       ::= { dbpPeerEntry  3 }

dbpPeerPortListen OBJECT-TYPE
       SYNTAX     Unsigned32 (1..65535)
       MAX-ACCESS read-write
       STATUS     current
       DESCRIPTION
             "The port the peer is listening on."
       ::= { dbpPeerEntry  4 }

dbpPeerTransportProtocol OBJECT-TYPE
       SYNTAX     INTEGER { tcp(1),
                            sctp(2) }
       MAX-ACCESS read-only
       STATUS     current
       DESCRIPTION
             "The transport protocol (tcp/sctp) the
              Diameter peer is using."
       ::= { dbpPeerEntry  5 }

dbpPeerSecurity OBJECT-TYPE
       SYNTAX     INTEGER { other(1),
                            tls(2),
                            ipsec(3) }
       MAX-ACCESS read-only
       STATUS     current
       DESCRIPTION
             "The security the Diameter peer is using.

              other(1) - Unknown Security Protocol
              tls(2)   - Transport Layer Security Protocol
              ipsec(3) - Internet Protocol Security"
       DEFVAL          { other }
       ::= { dbpPeerEntry  6 }

dbpPeerFirmwareRevision OBJECT-TYPE
       SYNTAX     SnmpAdminString
       MAX-ACCESS read-only
       STATUS     current
       DESCRIPTION
             "Firmware revision of peer.
              If the Entity MIB is supported by
              the node, then the contents of this object MUST be
              identical to those of the entPhysicalFirmwareRev
              object [RFC4133]. If no firmware
              revision, the revision of the Diameter software
              module may be reported instead."
       ::= { dbpPeerEntry 7 }

dbpPeerStorageType OBJECT-TYPE
    SYNTAX          StorageType
    MAX-ACCESS      read-create
    STATUS          current
    DESCRIPTION
            "The storage type for this conceptual row.
            Only the dbpPeerPortListen object is writable when
            the conceptual row is permanent."
    REFERENCE       "Textual Conventions for SMIv2, Section 2."
    DEFVAL          { nonVolatile }
    ::= { dbpPeerEntry 8 }

dbpPeerRowStatus OBJECT-TYPE
       SYNTAX     RowStatus
       MAX-ACCESS read-create
       STATUS     current
       DESCRIPTION
             "Status of the peer entry: creating the entry
              enables the peer, destroying the entry disables
              the peer."
       ::= {dbpPeerEntry 9 }

dbpPeerIpAddrTable OBJECT-TYPE
       SYNTAX     SEQUENCE OF DbpPeerIpAddrEntry
       MAX-ACCESS not-accessible
       STATUS     current
       DESCRIPTION
             "The table listing the Diameter
              peer IP addresses."
       ::= { dbpPeerCfgs 2 }

dbpPeerIpAddrEntry OBJECT-TYPE
       SYNTAX     DbpPeerIpAddrEntry
       MAX-ACCESS not-accessible
       STATUS     current
       DESCRIPTION
             "A row entry representing a
              the IP address of a Diameter peer."
       INDEX      {
                    dbpPeerIndex,
                    dbpPeerIpAddressIndex }
       ::= { dbpPeerIpAddrTable 1 }

DbpPeerIpAddrEntry ::= SEQUENCE {
       dbpPeerIpAddressIndex Unsigned32,
       dbpPeerIpAddressType  InetAddressType,
       dbpPeerIpAddress      InetAddress }

dbpPeerIpAddressIndex OBJECT-TYPE
       SYNTAX     Unsigned32 (1..4294967295)
       MAX-ACCESS not-accessible
       STATUS     current
       DESCRIPTION
             "A number uniquely identifying an IP Address
              supported by this Diameter peer."
       ::= { dbpPeerIpAddrEntry  1 }

dbpPeerIpAddressType OBJECT-TYPE
       SYNTAX      InetAddressType
       MAX-ACCESS  read-only
       STATUS      current
       DESCRIPTION
             "The type of address stored in dbpPeerIpAddress."
       ::= {dbpPeerIpAddrEntry 2}

dbpPeerIpAddress OBJECT-TYPE
       SYNTAX      InetAddress
       MAX-ACCESS  read-only
       STATUS      current
       DESCRIPTION
             "The active IP Address(es) used for connections."
       ::= {dbpPeerIpAddrEntry 3}

dbpAppAdvToPeerTable OBJECT-TYPE
       SYNTAX     SEQUENCE OF DbpAppAdvToPeerEntry
       MAX-ACCESS not-accessible
       STATUS     current
       DESCRIPTION
             "The table listing the applications advertised by
              this host to each peer and the types of service
              supported: accounting, authentication or both."
       ::= { dbpLocalCfgs 8 }

dbpAppAdvToPeerEntry OBJECT-TYPE
       SYNTAX     DbpAppAdvToPeerEntry
       MAX-ACCESS not-accessible
       STATUS     current
       DESCRIPTION
             "A row entry representing a discovered or
              configured Diameter peer."
       INDEX      { dbpPeerIndex,
                    dbpAppAdvToPeerVendorId,
                    dbpAppAdvToPeerIndex }
       ::= { dbpAppAdvToPeerTable 1 }

DbpAppAdvToPeerEntry ::= SEQUENCE {
       dbpAppAdvToPeerVendorId                 Unsigned32,
       dbpAppAdvToPeerIndex                    Unsigned32,
       dbpAppAdvToPeerServices                ServiceType,
       dbpAppAdvToPeerStorageType             StorageType,
       dbpAppAdvToPeerRowStatus                  RowStatus }

dbpAppAdvToPeerVendorId OBJECT-TYPE
       SYNTAX     Unsigned32 ( 1..4294967295 )
       MAX-ACCESS not-accessible
       STATUS     current
       DESCRIPTION
             "The IANA Enterprise Code value assigned to
              the vendor of the Diameter device."
       ::= { dbpAppAdvToPeerEntry  1 }

dbpAppAdvToPeerIndex OBJECT-TYPE
       SYNTAX     Unsigned32 ( 1..4294967295 )
       MAX-ACCESS not-accessible
       STATUS     current
       DESCRIPTION
             "A number uniquely identifying a Diameter
              application advertised as supported by
              this host to each peer.  Upon reload,
              dbpAppAdvToPeerIndex values may be
              changed"
       ::= { dbpAppAdvToPeerEntry  2 }

dbpAppAdvToPeerServices OBJECT-TYPE
       SYNTAX     ServiceType
       MAX-ACCESS read-only
       STATUS     current
       DESCRIPTION
             "The type of services supported for each application,
              accounting, authentication or both."
       ::= { dbpAppAdvToPeerEntry  3 }

dbpAppAdvToPeerStorageType OBJECT-TYPE
    SYNTAX          StorageType
    MAX-ACCESS      read-create
    STATUS          current
    DESCRIPTION
            "The storage type for this conceptual row.
            None of the objects are writable when the
            conceptual row is permanent."
    REFERENCE       "Textual Conventions for SMIv2, Section 2."
    DEFVAL          { nonVolatile }
    ::= { dbpAppAdvToPeerEntry 4 }

dbpAppAdvToPeerRowStatus OBJECT-TYPE
       SYNTAX     RowStatus
       MAX-ACCESS read-create
       STATUS     current
       DESCRIPTION
             "Status of the entry: creating the entry causes the
              application to be advertised, destroying the entry
              ceases advertisement."
       ::= { dbpAppAdvToPeerEntry  5 }

-- Applications advertised BY peers

dbpAppAdvFromPeerTable OBJECT-TYPE
    SYNTAX          SEQUENCE OF DbpAppAdvFromPeerEntry
    MAX-ACCESS      not-accessible
    STATUS          current
    DESCRIPTION
            "The table listing the applications advertised by
            each peer to this host and the types of service
            supported: accounting, authentication or both."
    ::= { dbpPeerCfgs 3 }

dbpAppAdvFromPeerEntry OBJECT-TYPE
    SYNTAX          DbpAppAdvFromPeerEntry
    MAX-ACCESS      not-accessible
    STATUS          current
    DESCRIPTION
            "A row entry representing a discovered or
            configured Diameter peer."
    INDEX           {
                        dbpPeerIndex,
                        dbpAppAdvFromPeerVendorId,
                        dbpAppAdvFromPeerIndex
                    }
    ::= { dbpAppAdvFromPeerTable 1 }

DbpAppAdvFromPeerEntry ::= SEQUENCE {
        dbpAppAdvFromPeerVendorId Unsigned32,
        dbpAppAdvFromPeerIndex    Unsigned32,
        dbpAppAdvFromPeerType     ServiceType
}

dbpAppAdvFromPeerVendorId OBJECT-TYPE
    SYNTAX          Unsigned32 (1..4294967295 )
    MAX-ACCESS      not-accessible
    STATUS          current
    DESCRIPTION
            "The IANA Enterprise Code value assigned to
            the vendor of the Diameter application."
    ::= { dbpAppAdvFromPeerEntry 1 }

dbpAppAdvFromPeerIndex OBJECT-TYPE
    SYNTAX          Unsigned32 (1..4294967295 )
    MAX-ACCESS      not-accessible
    STATUS          current
    DESCRIPTION
            "A number uniquely identifying the applications
            advertised as supported from each Diameter peer."
    ::= { dbpAppAdvFromPeerEntry 2 }

dbpAppAdvFromPeerType OBJECT-TYPE
    SYNTAX          ServiceType
    MAX-ACCESS      read-only
    STATUS          current
    DESCRIPTION
            "The type of services supported for each application,
            accounting, authentication or both."
    ::= { dbpAppAdvFromPeerEntry 3 }

-- table of vendor-IDs supported by each peer

dbpPeerVendorTable OBJECT-TYPE
    SYNTAX          SEQUENCE OF DbpPeerVendorEntry
    MAX-ACCESS      not-accessible
    STATUS          current
    DESCRIPTION
            "The table listing the Vendor IDs
            supported by the peer."
    ::= { dbpPeerCfgs 4 }

dbpPeerVendorEntry OBJECT-TYPE
    SYNTAX          DbpPeerVendorEntry
    MAX-ACCESS      not-accessible
    STATUS          current
    DESCRIPTION
            "A row entry representing a
            Vendor ID supported by the peer."
    INDEX           {
                        dbpPeerIndex,
                        dbpPeerVendorIndex
                    }
    ::= { dbpPeerVendorTable 1 }

DbpPeerVendorEntry ::= SEQUENCE {
        dbpPeerVendorIndex       Unsigned32,
        dbpPeerVendorId          INTEGER,
        dbpPeerVendorStorageType StorageType,
        dbpPeerVendorRowStatus   RowStatus
}

dbpPeerVendorIndex OBJECT-TYPE
    SYNTAX          Unsigned32 (1..4294967295)
    MAX-ACCESS      not-accessible
    STATUS          current
    DESCRIPTION
            "A number uniquely identifying the Vendor
            ID supported by the peer. Upon reload,
            dbpPeerVendorIndex values may be changed."
    ::= { dbpPeerVendorEntry 1 }

dbpPeerVendorId OBJECT-TYPE
    SYNTAX          INTEGER  {
                        diameterVendorIetf (0),
                        diameterVendorCisco (9),
                        diameterVendor3gpp (10415),
                        diameterVendorVodafone (12645)
                    }
    MAX-ACCESS      read-create
    STATUS          current
    DESCRIPTION
            "The active vendor ID used for peer connections.
            diameterVendorIetf (0)           -- IETF
            diameterVendorCisco (9)         -- Cisco Systems
            diameterVendor3gpp (10415)       --  3GPP
            diameterVendorVodafone (12645)     --- Vodafone"
    DEFVAL          { diameterVendorIetf }
    ::= { dbpPeerVendorEntry 2 }

dbpPeerVendorStorageType OBJECT-TYPE
    SYNTAX          StorageType
    MAX-ACCESS      read-create
    STATUS          current
    DESCRIPTION
            "The storage type for this conceptual row.
            None of the objects are writable when the
            conceptual row is permanent."
    REFERENCE       "Textual Conventions for SMIv2, Section 2."
    DEFVAL          { nonVolatile }
    ::= { dbpPeerVendorEntry 3 }

dbpPeerVendorRowStatus OBJECT-TYPE
    SYNTAX          RowStatus
    MAX-ACCESS      read-create
    STATUS          current
    DESCRIPTION
            "The status of this conceptual row.

            To create a row in this table, a manager must
            set this object to either createAndGo(4) or
            createAndWait(5).

            Until instances of all corresponding columns are
            appropriately configured, the value of the
            corresponding instance of the dbpPeerVendorRowStatus
            column is 'notReady'.

            In particular, a newly created row cannot be made
            active until the corresponding dbpPeerVendorId has been
            set. Also, a newly created row cannot be made active
            until the corresponding 'dbpPeerIndex' has been set.

            dbpPeerVendorId may not be modified while the
            value of this object is active(1):
            An attempt to set these objects while the value of
            dbpPeerVendorRowStatus is active(1) will result in
            an inconsistentValue error.

            Entries in this table with dbpPeerVendorRowStatus equal
            to active(1) remain in the table until destroyed.

            Entries in this table with dbpPeerVendorRowStatus equal
            to values other than active(1) will be destroyed after
            timeout (5 minutes)."
    ::= { dbpPeerVendorEntry 4 }

dbpPeerInfo OBJECT IDENTIFIER ::= { dbpPeerStats 5 }

dbpPerPeerInfoTable OBJECT-TYPE
       SYNTAX     SEQUENCE OF DbpPerPeerInfoEntry
       MAX-ACCESS not-accessible
       STATUS     current
       DESCRIPTION
             "The table listing Diameter per-peer information."
       ::= { dbpPeerInfo 1 }

dbpPerPeerInfoEntry OBJECT-TYPE
       SYNTAX     DbpPerPeerInfoEntry
       MAX-ACCESS not-accessible
       STATUS     current
       DESCRIPTION
             "A row entry representing a Diameter peer."
       INDEX     { dbpPeerIndex }
       ::= { dbpPerPeerInfoTable 1 }

DbpPerPeerInfoEntry ::= SEQUENCE {
       dbpPerPeerInfoState               Integer32,
       dbpPerPeerInfoStateDuration       TimeTicks,
       dbpPerPeerInfoLastDiscCause       Integer32,
       dbpPerPeerInfoWhoInitDisconnect   Integer32,
       dbpPerPeerStatsDWCurrentStatus     Integer32,
       dbpPerPeerStatsTimeoutConnAtmpts   Counter32,
       dbpPerPeerStatsASRsIn              Counter32,
       dbpPerPeerStatsASRsOut             Counter32,
       dbpPerPeerStatsASAsIn              Counter32,
       dbpPerPeerStatsASAsOut             Counter32,
       dbpPerPeerStatsACRsIn              Counter32,
       dbpPerPeerStatsACRsOut             Counter32,
       dbpPerPeerStatsACAsIn              Counter32,
       dbpPerPeerStatsACAsOut             Counter32,
       dbpPerPeerStatsCERsIn              Counter32,
       dbpPerPeerStatsCERsOut             Counter32,
       dbpPerPeerStatsCEAsIn              Counter32,
       dbpPerPeerStatsCEAsOut             Counter32,
       dbpPerPeerStatsDWRsIn              Counter32,
       dbpPerPeerStatsDWRsOut             Counter32,
       dbpPerPeerStatsDWAsIn              Counter32,
       dbpPerPeerStatsDWAsOut             Counter32,
       dbpPerPeerStatsDPRsIn              Counter32,
       dbpPerPeerStatsDPRsOut             Counter32,
       dbpPerPeerStatsDPAsIn              Counter32,
       dbpPerPeerStatsDPAsOut             Counter32,
       dbpPerPeerStatsRARsIn              Counter32,
       dbpPerPeerStatsRARsOut             Counter32,
       dbpPerPeerStatsRAAsIn              Counter32,
       dbpPerPeerStatsRAAsOut             Counter32,
       dbpPerPeerStatsSTRsIn              Counter32,
       dbpPerPeerStatsSTRsOut             Counter32,
       dbpPerPeerStatsSTAsIn              Counter32,
       dbpPerPeerStatsSTAsOut             Counter32,
       dbpPerPeerInfoDWReqTimer           TimeTicks,
       dbpPerPeerStatsRedirectEvents      Counter32,
       dbpPerPeerStatsAccDupRequests      Counter32,
       dbpPerPeerStatsMalformedReqsts     Counter32,
       dbpPerPeerStatsAccsNotRecorded     Counter32,
       dbpPerPeerStatsAccRetrans          Counter32,
       dbpPerPeerStatsTotalRetrans        Counter32,
       dbpPerPeerStatsAccPendReqstsOut    Gauge32,
       dbpPerPeerStatsAccReqstsDropped    Counter32,
       dbpPerPeerStatsHByHDropMessages    Counter32,
       dbpPerPeerStatsEToEDupMessages     Counter32,
       dbpPerPeerStatsUnknownTypes        Counter32,
       dbpPerPeerStatsProtocolErrors      Counter32,
       dbpPerPeerStatsTransientFailures   Counter32,
       dbpPerPeerStatsPermanentFailures   Counter32,
       dbpPerPeerStatsTransportDown       Counter32,
       dbpPeerIdentity			  SnmpAdminString }

dbpPerPeerInfoState OBJECT-TYPE
       SYNTAX     INTEGER { closed(1),
                            waitConnAck(2),
                            waitICea(3),
                            elect(4),
                            waitReturns(5),
                            rOpen(6),
                            iOpen(7),
                            closing(8) }
       MAX-ACCESS read-only
       STATUS     current
       DESCRIPTION
             "Connection state in the Peer State Machine of
              the peer with which this Diameter peer is
              communicating.

              closed      - Connection closed with this peer.
              waitConnAck - Waiting for an acknowledgment
                            from this peer.
              waitICea    - Waiting for a Capabilities-Exchange-Answer
                            from this peer.
              elect       - When the remote and local peers are both
                            trying to bring up a connection with
                            each other at the same time.  An
                            election process begins which
                            determines which socket remains open.
              waitReturns - Waiting for election returns.
              r-open      - Responder transport connection is
                            used for communication.
              i-open      - Initiator transport connection is
                            used for communication.
              closing     - Actively closing and doing cleanup."
       ::= { dbpPerPeerInfoEntry 1 }

dbpPerPeerInfoStateDuration OBJECT-TYPE
       SYNTAX     TimeTicks
       MAX-ACCESS read-only
       STATUS     current
       DESCRIPTION
             "The elapsed time (in hundredths of a second)
              since the last state change."
       ::= { dbpPerPeerInfoEntry 2 }

dbpPerPeerInfoLastDiscCause OBJECT-TYPE
       SYNTAX     INTEGER { rebooting(1),
                            busy(2),
                            doNotWantToTalk(3),
                            election(4) }
       MAX-ACCESS read-only
       STATUS     current
       DESCRIPTION
             "The last cause for a peer's disconnection.

              rebooting       - A scheduled reboot is imminent.
              busy            - The peer's internal resources are
                                constrained, and it has determined
                                that the transport connection needs
                                to be shutdown.
              doNotWantToTalk - The peer has determined that
                                it does not see a need for the
                                transport connection to exist,
                                since it does not expect any
                                messages to be exchanged in
                                the foreseeable future.
              electionLost    - The peer has determined that it
                                has lost the election process
                                and has therefore disconnected
                                the transport connection."
       ::= { dbpPerPeerInfoEntry 3 }

dbpPerPeerInfoWhoInitDisconnect OBJECT-TYPE
       SYNTAX     INTEGER { host(1),
                            peer(2) }
       MAX-ACCESS read-only
       STATUS     current
       DESCRIPTION
             "Did the host or peer initiate the disconnect?

              host - If this peer initiated the disconnect.
              peer - If the peer with which this peer was
                     connected initiated the disconnect."
       ::= { dbpPerPeerInfoEntry 4 }

dbpPerPeerStatsDWCurrentStatus OBJECT-TYPE
       SYNTAX     INTEGER { okay(1),
                            suspect(2),
                            down(3),
                            reopen(4) }
       MAX-ACCESS read-only
       STATUS     current
       DESCRIPTION
             "okay    - Indicates the connection is presumed working.
              suspect - Indicates the connection is possibly
                        congested or down.
              down    - The peer is no longer reachable, causing
                        the transport connection to be shutdown.
              reopen  - Three watchdog messages are exchanged with
                        accepted round trip times, and the connection
                        to the peer is considered stabilized."
       ::= { dbpPerPeerInfoEntry 5 }

dbpPerPeerStatsTimeoutConnAtmpts OBJECT-TYPE
       SYNTAX     Counter32 UNITS "connection attempts"
       MAX-ACCESS read-only
       STATUS     current
       DESCRIPTION
             "If there is no transport connection with a peer,
              this is the number of times the local peer has attempted
              to connect to that peer.  This is reset on
              connection."
       ::= { dbpPerPeerInfoEntry 6 }

dbpPerPeerStatsASRsIn OBJECT-TYPE
       SYNTAX     Counter32 UNITS "messages"
       MAX-ACCESS read-only
       STATUS     current
       DESCRIPTION
             "Number of Abort-Session-Request messages
              received from the peer."
       ::= { dbpPerPeerInfoEntry 7 }

dbpPerPeerStatsASRsOut OBJECT-TYPE
       SYNTAX     Counter32 UNITS "messages"
       MAX-ACCESS read-only
       STATUS     current
       DESCRIPTION
             "Number of Abort-Session-Request
              messages sent to the peer."
       ::= { dbpPerPeerInfoEntry 8 }

dbpPerPeerStatsASAsIn OBJECT-TYPE
       SYNTAX     Counter32 UNITS "messages"
       MAX-ACCESS read-only
       STATUS     current
       DESCRIPTION
             "Number of Abort-Session-Answer
              messages received from the peer."
       ::= { dbpPerPeerInfoEntry 9 }

dbpPerPeerStatsASAsOut OBJECT-TYPE
       SYNTAX     Counter32 UNITS "messages"
       MAX-ACCESS read-only
       STATUS     current
       DESCRIPTION
             "Number of Abort-Session-Answer
              messages sent to the peer."
       ::= { dbpPerPeerInfoEntry 10 }

dbpPerPeerStatsACRsIn OBJECT-TYPE
       SYNTAX     Counter32 UNITS "messages"
       MAX-ACCESS read-only
       STATUS     current
       DESCRIPTION
             "Number of Accounting-Request messages
              received from the peer."
       ::= { dbpPerPeerInfoEntry 11 }

dbpPerPeerStatsACRsOut OBJECT-TYPE
       SYNTAX     Counter32 UNITS "messages"
       MAX-ACCESS read-only
       STATUS     current
       DESCRIPTION
             "Number of Accounting-Request messages
              sent to the peer."
       ::= { dbpPerPeerInfoEntry 12 }

dbpPerPeerStatsACAsIn OBJECT-TYPE
       SYNTAX     Counter32 UNITS "messages"
       MAX-ACCESS read-only
       STATUS     current
       DESCRIPTION
             "Number of Accounting-Answer messages
              received from the peer."
       ::= { dbpPerPeerInfoEntry 13 }

dbpPerPeerStatsACAsOut OBJECT-TYPE
       SYNTAX     Counter32 UNITS "messages"
       MAX-ACCESS read-only
       STATUS     current
       DESCRIPTION
             "Number of Accounting-Answer messages
              sent to the peer."
       ::= { dbpPerPeerInfoEntry 14 }

dbpPerPeerStatsCERsIn OBJECT-TYPE
       SYNTAX     Counter32 UNITS "messages"
       MAX-ACCESS read-only
       STATUS     current
       DESCRIPTION
             "Number of Capabilities-Exchange-Request
              messages received from the peer."
       ::= { dbpPerPeerInfoEntry 15 }

dbpPerPeerStatsCERsOut OBJECT-TYPE
       SYNTAX     Counter32 UNITS "messages"
       MAX-ACCESS read-only
       STATUS     current
       DESCRIPTION
             "Number of Capabilities-Exchange-Request
              messages sent to the peer."
       ::= { dbpPerPeerInfoEntry 16 }

dbpPerPeerStatsCEAsIn OBJECT-TYPE
       SYNTAX     Counter32 UNITS "messages"
       MAX-ACCESS read-only
       STATUS     current
       DESCRIPTION
             "Number of Capabilities-Exchange-Answer
              messages received from the peer."
       ::= { dbpPerPeerInfoEntry 17 }

dbpPerPeerStatsCEAsOut OBJECT-TYPE
       SYNTAX     Counter32 UNITS "messages"
       MAX-ACCESS read-only
       STATUS     current
       DESCRIPTION
             "Number of Capabilities-Exchange-Answer
              messages sent to the peer."
       ::= { dbpPerPeerInfoEntry 18 }

dbpPerPeerStatsDWRsIn OBJECT-TYPE
       SYNTAX     Counter32 UNITS "messages"
       MAX-ACCESS read-only
       STATUS     current
       DESCRIPTION
             "Number of Device-Watchdog-Request
              messages received from the peer."
       ::= { dbpPerPeerInfoEntry 19 }

dbpPerPeerStatsDWRsOut OBJECT-TYPE
       SYNTAX     Counter32 UNITS "messages"
       MAX-ACCESS read-only
       STATUS     current
       DESCRIPTION
             "Number of Device-Watchdog-Request
              messages sent to the peer."
       ::= { dbpPerPeerInfoEntry 20 }

dbpPerPeerStatsDWAsIn OBJECT-TYPE
       SYNTAX     Counter32 UNITS "messages"
       MAX-ACCESS read-only
       STATUS     current
       DESCRIPTION
             "Number of Device-Watchdog-Answer
              messages received from the peer."
       ::= { dbpPerPeerInfoEntry 21 }

dbpPerPeerStatsDWAsOut OBJECT-TYPE
       SYNTAX     Counter32 UNITS "messages"
       MAX-ACCESS read-only
       STATUS     current
       DESCRIPTION
             "Number of Device-Watchdog-Answer
              messages sent to the peer."
       ::= { dbpPerPeerInfoEntry 22 }

dbpPerPeerStatsDPRsIn OBJECT-TYPE
       SYNTAX     Counter32 UNITS "messages"
       MAX-ACCESS read-only
       STATUS     current
       DESCRIPTION
             "Number of Disconnect-Peer-Request messages
              received."
       ::= { dbpPerPeerInfoEntry 23 }

dbpPerPeerStatsDPRsOut OBJECT-TYPE
       SYNTAX     Counter32 UNITS "messages"
       MAX-ACCESS read-only
       STATUS     current
       DESCRIPTION
             "Number of Disconnect-Peer-Request messages
              sent."
       ::= { dbpPerPeerInfoEntry 24 }

dbpPerPeerStatsDPAsIn OBJECT-TYPE
       SYNTAX     Counter32 UNITS "messages"
       MAX-ACCESS read-only
       STATUS     current
       DESCRIPTION
             "Number of Disconnect-Peer-Answer messages
              received."
       ::= { dbpPerPeerInfoEntry 25 }

dbpPerPeerStatsDPAsOut OBJECT-TYPE
       SYNTAX     Counter32 UNITS "messages"
       MAX-ACCESS read-only
       STATUS     current
       DESCRIPTION
             "Number of Disconnect-Peer-Answer messages
              sent."
       ::= { dbpPerPeerInfoEntry 26 }

dbpPerPeerStatsRARsIn  OBJECT-TYPE
       SYNTAX     Counter32 UNITS "messages"
       MAX-ACCESS read-only
       STATUS     current
       DESCRIPTION
             "Number of Re-Auth-Request messages
              received."
       ::= { dbpPerPeerInfoEntry 27 }

dbpPerPeerStatsRARsOut OBJECT-TYPE
       SYNTAX     Counter32 UNITS "messages"
       MAX-ACCESS read-only
       STATUS     current
       DESCRIPTION
             "Number of Re-Auth-Request messages
              sent."
       ::= { dbpPerPeerInfoEntry 28 }

dbpPerPeerStatsRAAsIn OBJECT-TYPE
       SYNTAX     Counter32 UNITS "messages"
       MAX-ACCESS read-only
       STATUS     current
       DESCRIPTION
             "Number of Re-Auth-Answer messages
              received."
       ::= { dbpPerPeerInfoEntry 29 }

dbpPerPeerStatsRAAsOut OBJECT-TYPE
       SYNTAX     Counter32 UNITS "messages"
       MAX-ACCESS read-only
       STATUS     current
       DESCRIPTION
             "Number of Re-Auth-Answer messages
              sent."
       ::= { dbpPerPeerInfoEntry 30 }

dbpPerPeerStatsSTRsIn OBJECT-TYPE
       SYNTAX     Counter32 UNITS "messages"
       MAX-ACCESS read-only
       STATUS     current
       DESCRIPTION
             "Number of Session-Termination-Request
              messages received from the peer."
       ::= { dbpPerPeerInfoEntry 31 }

dbpPerPeerStatsSTRsOut OBJECT-TYPE
       SYNTAX     Counter32 UNITS "messages"
       MAX-ACCESS read-only
       STATUS     current
       DESCRIPTION
             "Number of Session-Termination-Request
              messages sent to the peer."
       ::= { dbpPerPeerInfoEntry 32 }

dbpPerPeerStatsSTAsIn OBJECT-TYPE
       SYNTAX     Counter32 UNITS "messages"
       MAX-ACCESS read-only
       STATUS     current
       DESCRIPTION
             "Number of Session-Termination-Answer
              messages received from the peer."
       ::= { dbpPerPeerInfoEntry 33 }

dbpPerPeerStatsSTAsOut OBJECT-TYPE
       SYNTAX     Counter32 UNITS "messages"
       MAX-ACCESS read-only
       STATUS     current
       DESCRIPTION
             "Number of Session-Termination-Answer
              messages sent to the peer."
       ::= { dbpPerPeerInfoEntry 34 }

dbpPerPeerInfoDWReqTimer OBJECT-TYPE
       SYNTAX     TimeTicks
       MAX-ACCESS read-only
       STATUS     current
       DESCRIPTION
             "Device-Watchdog Request Timer, which
              is the interval between messages sent to
              peers."
       ::= { dbpPerPeerInfoEntry 35 }

dbpPerPeerStatsRedirectEvents OBJECT-TYPE
       SYNTAX     Counter32 UNITS "messages"
       MAX-ACCESS read-only
       STATUS     current
       DESCRIPTION
             "Redirect Event count, which is the number
              of redirects sent from a peer."
       ::= { dbpPerPeerInfoEntry 36 }

dbpPerPeerStatsAccDupRequests OBJECT-TYPE
       SYNTAX     Counter32 UNITS "messages"
       MAX-ACCESS read-only
       STATUS     current
       DESCRIPTION
             "The number of duplicate Diameter Accounting-Request
              messages received."
       ::= { dbpPerPeerInfoEntry 37 }

dbpPerPeerStatsMalformedReqsts OBJECT-TYPE
       SYNTAX     Counter32 UNITS "messages"
       MAX-ACCESS read-only
       STATUS     current
       DESCRIPTION
             "The number of malformed Diameter
              messages received."
       ::= { dbpPerPeerInfoEntry 38 }

dbpPerPeerStatsAccsNotRecorded OBJECT-TYPE
       SYNTAX     Counter32 UNITS "messages"
       MAX-ACCESS read-only
       STATUS     current
       DESCRIPTION
             "The number of Diameter Accounting-Request messages
              which were received and responded to but not
              recorded."
       ::= { dbpPerPeerInfoEntry 39 }

dbpPerPeerStatsAccRetrans OBJECT-TYPE
       SYNTAX     Counter32 UNITS "messages"
       MAX-ACCESS read-only
       STATUS     current
       DESCRIPTION
             "The number of Diameter Accounting-Request messages
              retransmitted to this Diameter peer."
       ::= { dbpPerPeerInfoEntry 40 }

dbpPerPeerStatsTotalRetrans OBJECT-TYPE
       SYNTAX     Counter32 UNITS "messages"
       MAX-ACCESS read-only
       STATUS     current
       DESCRIPTION
             "The number of Diameter messages retransmitted
              to this Diameter peer, not to include Diameter
              Accounting-Request messages retransmitted."
       ::= { dbpPerPeerInfoEntry 41 }

dbpPerPeerStatsAccPendReqstsOut OBJECT-TYPE
       SYNTAX     Gauge32
       MAX-ACCESS read-only
       STATUS     current
       DESCRIPTION
          "The number of Diameter Accounting-Request messages
           sent to this peer that have not yet timed out or
           received a response. This variable is incremented when an
           Accounting-Request is received by this server and decremented
           due to the transmission of an Accounting-Response, a timeout
           or a retransmission."
       ::= { dbpPerPeerInfoEntry 42 }

dbpPerPeerStatsAccReqstsDropped OBJECT-TYPE
       SYNTAX     Counter32 UNITS "messages"
       MAX-ACCESS read-only
       STATUS     current
       DESCRIPTION
          "The number of Accounting-Requests to this server
           that have been dropped."
       ::= { dbpPerPeerInfoEntry 43 }

dbpPerPeerStatsHByHDropMessages OBJECT-TYPE
       SYNTAX     Counter32 UNITS "messages"
       MAX-ACCESS read-only
       STATUS     current
       DESCRIPTION
             "An answer message that is received with an unknown
              Hop-by-Hop Identifier.  Does not include Accounting
              Requests dropped."
       ::= { dbpPerPeerInfoEntry 44 }

dbpPerPeerStatsEToEDupMessages OBJECT-TYPE
       SYNTAX     Counter32 UNITS "messages"
       MAX-ACCESS read-only
       STATUS     current
       DESCRIPTION
             "Duplicate answer messages that are to be locally
              consumed.  Does not include duplicate Accounting
              Requests received."
       ::= { dbpPerPeerInfoEntry 45 }

dbpPerPeerStatsUnknownTypes OBJECT-TYPE
       SYNTAX     Counter32 UNITS "messages"
       MAX-ACCESS read-only
       STATUS     current
       DESCRIPTION
             "The number of Diameter messages of unknown type
              which were received."
       ::= { dbpPerPeerInfoEntry 46 }

dbpPerPeerStatsProtocolErrors OBJECT-TYPE
       SYNTAX     Counter32 UNITS "errors"
       MAX-ACCESS read-only
       STATUS     current
       DESCRIPTION
             "Number of protocol errors returned to peer,
              but not including redirects.
              Error Code 3xxx indicate Protocol Failure"
       ::= { dbpPerPeerInfoEntry 47 }

dbpPerPeerStatsTransientFailures OBJECT-TYPE
       SYNTAX     Counter32 UNITS "errors"
       MAX-ACCESS read-only
       STATUS     current
       DESCRIPTION
             "Transient Failure count.
             Error Code 4xxx indicate Transient Failure."
       ::= { dbpPerPeerInfoEntry 48 }

dbpPerPeerStatsPermanentFailures OBJECT-TYPE
       SYNTAX     Counter32 UNITS "errors"
       MAX-ACCESS read-only
       STATUS     current
       DESCRIPTION
             "Number of permanent failures returned to peer.
              Error Code 5xxx indicate Permanent Failure."
       ::= { dbpPerPeerInfoEntry 49 }

dbpPerPeerStatsTransportDown OBJECT-TYPE
       SYNTAX     Counter32 UNITS "errors"
       MAX-ACCESS read-only
       STATUS     current
       DESCRIPTION
             "Number of unexpected transport failures."
       ::= { dbpPerPeerInfoEntry 50 }
       
       
       
   dbpPeerIdentity OBJECT-TYPE
       SYNTAX     SnmpAdminString 
       MAX-ACCESS read-only
       STATUS     current
       DESCRIPTION
             "Represents Diameter Peer Identity."
       ::= { dbpPerPeerInfoEntry 51 }    
       
       


-- Realm-based Routing Table

dbpRealmMessageRouteTable OBJECT-TYPE
       SYNTAX     SEQUENCE OF DbpRealmMessageRouteEntry
       MAX-ACCESS not-accessible
       STATUS     current
       DESCRIPTION
             "The table listing the Diameter
              Realm-based Message Route information."
       ::= { dbpRealmStats 1 }

dbpRealmMessageRouteEntry OBJECT-TYPE
       SYNTAX     DbpRealmMessageRouteEntry
       MAX-ACCESS not-accessible
       STATUS     current
       DESCRIPTION
             "A row entry representing a Diameter
              Realm Based Message Route."
       INDEX      { dbpRealmMessageRouteIndex }
       ::= { dbpRealmMessageRouteTable 1 }

DbpRealmMessageRouteEntry ::= SEQUENCE {
       dbpRealmMessageRouteIndex              Unsigned32,
       dbpRealmMessageRouteRealm         SnmpAdminString,
       dbpRealmMessageRouteApp                Unsigned32,
       dbpRealmMessageRouteType              ServiceType,
       dbpRealmMessageRouteAction              Integer32,
       dbpRealmMessageRouteACRsIn              Counter32,
       dbpRealmMessageRouteACRsOut             Counter32,
       dbpRealmMessageRouteACAsIn              Counter32,
       dbpRealmMessageRouteACAsOut             Counter32,
       dbpRealmMessageRouteRARsIn              Counter32,
       dbpRealmMessageRouteRARsOut             Counter32,
       dbpRealmMessageRouteRAAsIn              Counter32,
       dbpRealmMessageRouteRAAsOut             Counter32,
       dbpRealmMessageRouteSTRsIn              Counter32,
       dbpRealmMessageRouteSTRsOut             Counter32,
       dbpRealmMessageRouteSTAsIn              Counter32,
       dbpRealmMessageRouteSTAsOut             Counter32,
       dbpRealmMessageRouteASRsIn              Counter32,
       dbpRealmMessageRouteASRsOut             Counter32,
       dbpRealmMessageRouteASAsIn              Counter32,
       dbpRealmMessageRouteASAsOut             Counter32,
       dbpRealmMessageRouteAccRetrans          Counter32,
       dbpRealmMessageRouteAccDupReqsts        Counter32,
       dbpRealmMessageRoutePendReqstsOut         Gauge32,
       dbpRealmMessageRouteReqstsDrop          Counter32 }

dbpRealmMessageRouteIndex OBJECT-TYPE
       SYNTAX     Unsigned32 (1..4294967295)
       MAX-ACCESS not-accessible
       STATUS     current
       DESCRIPTION
             "A number uniquely identifying each Realm."
       ::= { dbpRealmMessageRouteEntry 1 }

dbpRealmMessageRouteRealm OBJECT-TYPE
       SYNTAX     SnmpAdminString
       MAX-ACCESS read-only
       STATUS     current
       DESCRIPTION
             "Realm name"
       ::= { dbpRealmMessageRouteEntry 2 }

dbpRealmMessageRouteApp OBJECT-TYPE
       SYNTAX     Unsigned32 (1..4294967295)
       MAX-ACCESS read-only
       STATUS     current
       DESCRIPTION
             "Application id used to route messages
              to this realm."
       ::= { dbpRealmMessageRouteEntry 3 }

dbpRealmMessageRouteType OBJECT-TYPE
       SYNTAX     ServiceType
       MAX-ACCESS read-only
       STATUS     current
       DESCRIPTION
             "The types of service supported for each
              realm application: accounting,
              authentication or both."
       ::= { dbpRealmMessageRouteEntry 4 }

dbpRealmMessageRouteAction OBJECT-TYPE
       SYNTAX     INTEGER { local(1),
                            relay(2),
                            proxy(3),
                            redirect(4) }
       MAX-ACCESS read-only
       STATUS     current
       DESCRIPTION
             "The action is used to identify how a
              message should be treated based on the realm,
              application and type.
              local    - Diameter messages that resolve to a
                         route entry with the Local Action set to
                         Local can be satisfied locally, and do
                         not need to be routed to another peer.
              relay    - All Diameter messages that fall within
                         this category MUST be routed to a
                         next-hop peer, without modifying any
                         non-routing AVPs.
              proxy    - All Diameter messages that fall within this
                         category MUST be routed to a next-hop
                         peer.
              redirect - Diameter messages that fall within this
                         category MUST have the identity of the home
                         Diameter peer(s) appended, and returned
                         to the sender of the message."
       ::= { dbpRealmMessageRouteEntry 5 }

-- Per-realm message statistics

dbpRealmMessageRouteACRsIn OBJECT-TYPE
       SYNTAX     Counter32 UNITS "messages"
       MAX-ACCESS read-only
       STATUS     current
       DESCRIPTION
             "Number of Accounting-Request messages
              received from the realm."
       ::= { dbpRealmMessageRouteEntry 6 }

dbpRealmMessageRouteACRsOut OBJECT-TYPE
       SYNTAX     Counter32 UNITS "messages"
       MAX-ACCESS read-only
       STATUS     current
       DESCRIPTION
             "Number of Accounting-Request messages
              sent to the realm."
       ::= { dbpRealmMessageRouteEntry 7 }

dbpRealmMessageRouteACAsIn OBJECT-TYPE
       SYNTAX     Counter32 UNITS "messages"
       MAX-ACCESS read-only
       STATUS     current
       DESCRIPTION
             "Number of Accounting-Answer messages
              received from the realm."
       ::= { dbpRealmMessageRouteEntry 8 }

dbpRealmMessageRouteACAsOut OBJECT-TYPE
       SYNTAX     Counter32 UNITS "messages"
       MAX-ACCESS read-only
       STATUS     current
       DESCRIPTION
             "Number of Accounting-Answer messages
              sent to the realm."
       ::= { dbpRealmMessageRouteEntry 9 }

dbpRealmMessageRouteRARsIn OBJECT-TYPE
       SYNTAX     Counter32 UNITS "messages"
       MAX-ACCESS read-only
       STATUS     current
       DESCRIPTION
             "Number of Re-Auth-Request messages
              received from the realm."
       ::= { dbpRealmMessageRouteEntry 10 }

dbpRealmMessageRouteRARsOut OBJECT-TYPE
       SYNTAX     Counter32 UNITS "messages"
       MAX-ACCESS read-only
       STATUS     current
       DESCRIPTION
             "Number of Re-Auth-Request messages
              sent to the realm."
       ::= { dbpRealmMessageRouteEntry 11 }

dbpRealmMessageRouteRAAsIn OBJECT-TYPE
       SYNTAX     Counter32 UNITS "messages"
       MAX-ACCESS read-only
       STATUS     current
       DESCRIPTION
             "Number of Re-Auth-Answer messages
              received from the realm."
       ::= { dbpRealmMessageRouteEntry 12 }

dbpRealmMessageRouteRAAsOut OBJECT-TYPE
       SYNTAX     Counter32 UNITS "messages"
       MAX-ACCESS read-only
       STATUS     current
       DESCRIPTION
             "Number of Re-Auth-Answer messages
              sent to the realm."
       ::= { dbpRealmMessageRouteEntry 13 }

dbpRealmMessageRouteSTRsIn OBJECT-TYPE
       SYNTAX     Counter32 UNITS "messages"
       MAX-ACCESS read-only
       STATUS     current
       DESCRIPTION
             "Number of Session-Termination-Request messages
              received from the realm."
       ::= { dbpRealmMessageRouteEntry 14 }

dbpRealmMessageRouteSTRsOut OBJECT-TYPE
       SYNTAX     Counter32 UNITS "messages"
       MAX-ACCESS read-only
       STATUS     current
       DESCRIPTION
             "Number of Session-Termination-Request messages
              sent to the realm."
       ::= { dbpRealmMessageRouteEntry 15 }

dbpRealmMessageRouteSTAsIn OBJECT-TYPE
       SYNTAX     Counter32 UNITS "messages"
       MAX-ACCESS read-only
       STATUS     current
       DESCRIPTION
             "Number of Session-Termination-Answer messages
              received from the realm."
       ::= { dbpRealmMessageRouteEntry 16 }

dbpRealmMessageRouteSTAsOut OBJECT-TYPE
       SYNTAX     Counter32 UNITS "messages"
       MAX-ACCESS read-only
       STATUS     current
       DESCRIPTION
             "Number of Session-Termination-Answer messages
              sent to the realm."
       ::= { dbpRealmMessageRouteEntry 17 }

dbpRealmMessageRouteASRsIn OBJECT-TYPE
       SYNTAX     Counter32 UNITS "messages"
       MAX-ACCESS read-only
       STATUS     current
       DESCRIPTION
             "Number of Abort-Session-Request messages
              received from the realm."
       ::= { dbpRealmMessageRouteEntry 18 }

dbpRealmMessageRouteASRsOut OBJECT-TYPE
       SYNTAX     Counter32 UNITS "messages"
       MAX-ACCESS read-only
       STATUS     current
       DESCRIPTION
             "Number of Abort-Session-Request messages
              sent to the realm."
       ::= { dbpRealmMessageRouteEntry 19 }

dbpRealmMessageRouteASAsIn OBJECT-TYPE
       SYNTAX     Counter32 UNITS "messages"
       MAX-ACCESS read-only
       STATUS     current
       DESCRIPTION
             "Number of Abort-Session-Answer messages
              received from the realm."
       ::= { dbpRealmMessageRouteEntry 20 }

dbpRealmMessageRouteASAsOut OBJECT-TYPE
       SYNTAX     Counter32 UNITS "messages"
       MAX-ACCESS read-only
       STATUS     current
       DESCRIPTION
             "Number of Abort-Session-Answer messages
              sent to the realm."
       ::= { dbpRealmMessageRouteEntry 21 }

dbpRealmMessageRouteAccRetrans OBJECT-TYPE
       SYNTAX     Counter32 UNITS "messages"
       MAX-ACCESS read-only
       STATUS     current
       DESCRIPTION
             "The number of Diameter accounting messages
              retransmitted to this realm."
       ::= { dbpRealmMessageRouteEntry 22 }

dbpRealmMessageRouteAccDupReqsts OBJECT-TYPE
       SYNTAX     Counter32 UNITS "messages"
       MAX-ACCESS read-only
       STATUS     current
       DESCRIPTION
             "The number of duplicate Diameter accounting
              messages sent to this realm."
       ::= { dbpRealmMessageRouteEntry 23 }

dbpRealmMessageRoutePendReqstsOut OBJECT-TYPE
       SYNTAX     Gauge32
       MAX-ACCESS read-only
       STATUS     current
       DESCRIPTION
          "The number of Diameter Accounting-Request messages
           sent to this peer that have not yet timed out or
           received a response. This variable is incremented when an
           Accounting-Request is sent to this peer and decremented
           due to receipt of an Accounting-Response, a timeout or
           a retransmission."
       ::= { dbpRealmMessageRouteEntry 24 }

dbpRealmMessageRouteReqstsDrop OBJECT-TYPE
       SYNTAX     Counter32 UNITS "messages"
       MAX-ACCESS read-only
       STATUS     current
       DESCRIPTION
             "The number of requsts dropped by this realm."
       ::= { dbpRealmMessageRouteEntry 25 }

dbpRealmKnownPeersTable OBJECT-TYPE
       SYNTAX     SEQUENCE OF DbpRealmKnownPeersEntry
       MAX-ACCESS not-accessible
       STATUS     current
       DESCRIPTION
             "The table listing the Diameter
              Realms and known peers.
              This is an ordered list, where the ordering
              signifies the order in which the peers are
              tried."
       ::= { dbpRealmCfgs 1 }

dbpRealmKnownPeersEntry OBJECT-TYPE
       SYNTAX     DbpRealmKnownPeersEntry
       MAX-ACCESS not-accessible
       STATUS     current
       DESCRIPTION
             "A row entry representing a Diameter
              Realm and known peers."
       INDEX      { dbpRealmMessageRouteIndex,
                    dbpRealmKnownPeersIndex }
       ::= { dbpRealmKnownPeersTable 1 }

DbpRealmKnownPeersEntry ::= SEQUENCE {
       dbpRealmKnownPeersIndex                Unsigned32,
       dbpRealmKnownPeers                     Unsigned32,
       dbpRealmKnownPeersChosen                  Integer32 }

dbpRealmKnownPeersIndex OBJECT-TYPE
       SYNTAX     Unsigned32 (1..4294967295)
       MAX-ACCESS not-accessible
       STATUS     current
       DESCRIPTION
             "A sequential identifier number."
       ::= { dbpRealmKnownPeersEntry 1 }

dbpRealmKnownPeers OBJECT-TYPE
       SYNTAX     Unsigned32 (1..4294967295)
       MAX-ACCESS read-only
       STATUS     current
       DESCRIPTION
             "The index of the peer this realm knows about.
              Same as the dbpPeerIndex"
       ::= { dbpRealmKnownPeersEntry 2 }

dbpRealmKnownPeersChosen OBJECT-TYPE
       SYNTAX     INTEGER { other(1),
                            roundRobin(2),
                            loadBalance(3),
                            firstPreferred(4),
                            mostRecentFirst(5) }
       MAX-ACCESS read-only
       STATUS     current
       DESCRIPTION
             "How the realm chooses which peer to send
              messages to.
              roundRobin      - The peer used for each transaction
                                is selected based on the order in
                                which peers are configured.
              loadBalance     - The peer used for each transaction
                                is based on the load metric (
                                implementation dependent) of all
                                peers defined for the realm, with
                                the least loaded peer selected
                                first.
              firstPreferred  - The first defined peer is always
                                used for transactions unless
                                failover occurs.
              mostRecentFirst - The most recently used peer is
                                used first for each transaction."
       ::= { dbpRealmKnownPeersEntry 3 }


-- Conformance

diameterBaseProtocolMIBCompliances
                    OBJECT IDENTIFIER ::= { diameterBaseConform 1 }

diameterBaseProtocolMIBGroups
                    OBJECT IDENTIFIER ::= { diameterBaseConform 2 }

-- Compliance Statements

diameterBPMIBCompliances MODULE-COMPLIANCE
       STATUS     current
       DESCRIPTION
            "The compliance statement for Diameter Base
             Protocol entities."
       MODULE -- this module
            MANDATORY-GROUPS {
                               dbpLocalCfgGroup,
                               dbpPeerCfgGroup,
                               dbpPeerStatsGroup,
                               dbpNotificationsGroup,
                               dbpNotifCfgGroup }

            GROUP              dbpLocalCfgSkippedGroup
            DESCRIPTION
               "This group is only mandatory for a system that
                implements all the local config objects."

            GROUP              dbpLocalStatsSkippedGroup
            DESCRIPTION
               "This group is only mandatory for a system that
                implements all the local statistics objects."

            GROUP              dbpPeerCfgSkippedGroup
            DESCRIPTION
               "This group is only mandatory for a system that
                implements all the peer config objects."

            GROUP              dbpPeerStatsSkippedGroup
            DESCRIPTION
               "This group is only mandatory for a system that
                implements all the peer statistic objects."

            GROUP              dbpRealmCfgSkippedGroup
            DESCRIPTION
               "This group is only mandatory for a system that
                implementsall the realm config objects."

            GROUP              dbpRealmStatsSkippedGroup
            DESCRIPTION
               "This group is only mandatory for a system that
                implements all the realm statistic objects."

       ::= { diameterBaseProtocolMIBCompliances 1 }

-- Units of Conformance

dbpLocalCfgGroup OBJECT-GROUP
      OBJECTS {
              dbpLocalRealm,
              dbpLocalOriginHost,
              dbpLocalVendorId,
              dbpLocalVendorStorageType,
              dbpLocalVendorRowStatus
      }
      STATUS  current
      DESCRIPTION
            "A collection of objects providing configuration common
             to the peer."
      ::= { diameterBaseProtocolMIBGroups 1 }

dbpPeerCfgGroup OBJECT-GROUP
    OBJECTS   {
              dbpPeerId,
              dbpPeerPortConnect,
              dbpPeerPortListen,
              dbpPeerProtocol,
              dbpPeerSecurity,
              dbpPeerFirmwareRevision,
              dbpPeerStorageType,
              dbpPeerRowStatus,
              dbpPeerIpAddressType,
              dbpPeerIpAddress,
              dbpPeerVendorId,
              dbpPeerVendorStorageType,
              dbpPeerVendorRowStatus
    }
    STATUS          current
    DESCRIPTION
            "A collection of objects providing configuration
            of the Diameter peers."
    ::= { diameterBaseProtocolMIBGroups 2 }

dbpPeerStatsGroup OBJECT-GROUP
    OBJECTS   {
              dbpPeerStatsState,
              dbpPeerStatsStateDuration,
              dbpPeerStatsLastDiscCause,
              dbpPeerStatsWhoInitDisconnect,
              dbpPeerStatsDWCurrentStatus,
              dbpPeerStatsTimeoutConnAtmpts,
              dbpPeerStatsASRsIn,
              dbpPeerStatsASRsOut,
              dbpPeerStatsASAsIn,
              dbpPeerStatsASAsOut,
              dbpPeerStatsACRsIn,
              dbpPeerStatsACRsOut,
              dbpPeerStatsACAsIn,
              dbpPeerStatsACAsOut,
              dbpPeerStatsCERsIn,
              dbpPeerStatsCERsOut,
              dbpPeerStatsCEAsIn,
              dbpPeerStatsCEAsOut,
              dbpPeerStatsDWRsIn,
              dbpPeerStatsDWRsOut,
              dbpPeerStatsDWAsIn,
              dbpPeerStatsDWAsOut,
              dbpPeerStatsDPRsIn,
              dbpPeerStatsDPRsOut,
              dbpPeerStatsDPAsIn,
              dbpPeerStatsDPAsOut,
              dbpPeerStatsRARsIn,
              dbpPeerStatsRARsOut,
              dbpPeerStatsRAAsIn,
              dbpPeerStatsRAAsOut,
              dbpPeerStatsSTRsIn,
              dbpPeerStatsSTRsOut,
              dbpPeerStatsSTAsIn,
              dbpPeerStatsSTAsOut,
              dbpPeerStatsDWReqTimer,
              dbpPeerStatsRedirectEvents,
              dbpPeerStatsAccDupRequests,
              dbpPeerStatsMalformedReqsts,
              dbpPeerStatsAccsNotRecorded,
              dbpPeerStatsAccRetrans,
              dbpPeerStatsTotalRetrans,
              dbpPeerStatsAccPendReqstsOut,
              dbpPeerStatsAccReqstsDropped,
              dbpPeerStatsHByHDropMessages,
              dbpPeerStatsEToEDupMessages,
              dbpPeerStatsUnknownTypes,
              dbpPeerStatsProtocolErrors,
              dbpPeerStatsTransientFailures,
              dbpPeerStatsPermanentFailures,
              dbpPeerStatsTransportDown
    }
    STATUS          current
    DESCRIPTION
            "A collection of objects providing statistics
             of the Diameter peers."
    ::= { diameterBaseProtocolMIBGroups 3 }

dbpNotificationsGroup NOTIFICATION-GROUP
   NOTIFICATIONS    {
                    dbpProtocolErrorNotif,
                    dbpTransientFailureNotif,
                    dbpPermanentFailureNotif,
                    dbpPeerConnectionDownNotif,
                    dbpPeerConnectionUpNotif
                    }
    STATUS          current
    DESCRIPTION
            "The set of notifications which an agent is required
             to implement."
    ::= { diameterBaseProtocolMIBGroups 4 }

dbpNotifCfgGroup OBJECT-GROUP
    OBJECTS         {
                    dbpProtocolErrorNotifEnabled,
                    dbpTransientFailureNotifEnabled,
                    dbpPermanentFailureNotifEnabled,
                    dbpPeerConnectionDownNotifEnabled,
                    dbpPeerConnectionUpNotifEnabled
                    }
    STATUS          current
    DESCRIPTION
            "A collection of objects providing configuration for
            base protocol notifications."
    ::= { diameterBaseProtocolMIBGroups 5 }

dbpLocalCfgSkippedGroup OBJECT-GROUP
    OBJECTS         {
                    dbpLocalId,
                    dbpLocalTcpListenPort,
                    dbpLocalSctpListenPort,
                    dbpLocalStatsTotalPacketsIn,
                    dbpLocalStatsTotalPacketsOut,
                    dbpLocalStatsTotalUpTime,
                    dbpLocalResetTime,
                    dbpLocalConfigReset,
                    dbpLocalApplStorageType,
                    dbpLocalApplRowStatus,
                    dbpAppAdvToPeerServices,
                    dbpAppAdvToPeerStorageType,
                    dbpAppAdvToPeerRowStatus
                    }
    STATUS          current
    DESCRIPTION
            "A collection of objects providing configuration common
            to the peer."
    ::= { diameterBaseProtocolMIBGroups 6 }


dbpLocalStatsSkippedGroup OBJECT-GROUP
    OBJECTS         {
                    dbpLocalStatsTotalPacketsIn,
                    dbpLocalStatsTotalPacketsOut,
                    dbpLocalStatsTotalUpTime,
                    dbpLocalResetTime,
                    dbpLocalConfigReset
                    }
    STATUS          current
    DESCRIPTION
            "A collection of objects providing statistics common
            to the peer."
    ::= { diameterBaseProtocolMIBGroups 7 }

dbpPeerCfgSkippedGroup OBJECT-GROUP
    OBJECTS         { cdbpAppAdvFromPeerType }
    STATUS          current
    DESCRIPTION
            "A collection of objects providing configuration for
            Diameter peers."
    ::= { diameterBaseProtocolMIBGroups 8 }

dbpPeerStatsSkippedGroup OBJECT-GROUP
    OBJECTS         {
                    dbpPeerStatsDWCurrentStatus,
                    dbpPeerStatsDWReqTimer,
                    dbpPeerStatsRedirectEvents,
                    dbpPeerStatsAccDupRequests,
                    dbpPeerStatsEToEDupMessages
                    }
    STATUS          current
    DESCRIPTION
            "A collection of objects providing statistics
            of Diameter peers."
    ::= { diameterBaseProtocolMIBGroups 9 }

dbpRealmCfgSkippedGroup OBJECT-GROUP
    OBJECTS         {
                    dbpRealmKnownPeers,
                    dbpRealmKnownPeersChosen
                    }
    STATUS          current
    DESCRIPTION
            "A collection of objects providing configuration for
            realm message routing."
    ::= { diameterBaseProtocolMIBGroups 10 }

dbpRealmStatsSkippedGroup OBJECT-GROUP
    OBJECTS         {
                    dbpRealmMessageRouteRealm,
                    dbpRealmMessageRouteApp,
                    dbpRealmMessageRouteType,
                    dbpRealmMessageRouteAction,
                    dbpRealmMessageRouteACRsIn,
                    dbpRealmMessageRouteACRsOut,
                    dbpRealmMessageRouteACAsIn,
                    dbpRealmMessageRouteACAsOut,
                    dbpRealmMessageRouteRARsIn,
                    dbpRealmMessageRouteRARsOut,
                    dbpRealmMessageRouteRAAsIn,
                    dbpRealmMessageRouteRAAsOut,
                    dbpRealmMessageRouteSTRsIn,
                    dbpRealmMessageRouteSTRsOut,
                    dbpRealmMessageRouteSTAsIn,
                    dbpRealmMessageRouteSTAsOut,
                    dbpRealmMessageRouteASRsIn,
                    dbpRealmMessageRouteASRsOut,
                    dbpRealmMessageRouteASAsIn,
                    dbpRealmMessageRouteASAsOut,
                    dbpRealmMessageRouteAccRetrans,
                    dbpRealmMessageRouteAccDupReqsts,
                    dbpRealmMessageRoutePendReqstsOut,
                    dbpRealmMessageRouteReqstsDrop
                    }
    STATUS          current
    DESCRIPTION
            "A collection of objects providing statistics
            of realm message routing."
    ::= { diameterBaseProtocolMIBGroups 11 }

END
