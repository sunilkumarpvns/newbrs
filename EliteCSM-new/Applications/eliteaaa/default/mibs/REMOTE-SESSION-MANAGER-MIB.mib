REMOTE-SESSION-MANAGER-MIB DEFINITIONS ::= BEGIN

IMPORTS
       MODULE-IDENTITY, OBJECT-TYPE, OBJECT-IDENTITY,
       Counter32, Integer32,
       IpAddress, TimeTicks, mib-2      FROM SNMPv2-SMI
       SnmpAdminString                  FROM SNMP-FRAMEWORK-MIB
       MODULE-COMPLIANCE, OBJECT-GROUP  FROM SNMPv2-CONF;
       

        internet      OBJECT IDENTIFIER ::= { iso org(3) dod(6) 1 }

        directory     OBJECT IDENTIFIER ::= { internet 1 }

        mgmt          OBJECT IDENTIFIER ::= { internet 2 }
 
        experimental  OBJECT IDENTIFIER ::= { internet 3 }

        private       OBJECT IDENTIFIER ::= { internet 4 }

        enterprises   OBJECT IDENTIFIER ::= { private 1 }

        elitecore     OBJECT IDENTIFIER ::= { enterprises 21067 }
                    
        radius       OBJECT IDENTIFIER ::= { elitecore 1 }
        
        sessionManagerMIB   OBJECT IDENTIFIER ::= { radius 2 }

remoteSessionManagerMIBObjects OBJECT IDENTIFIER ::= { sessionManagerMIB 2 }

remoteSessionManagerStatTable OBJECT-TYPE
       SYNTAX     SEQUENCE OF RemoteSessionManagerEntry
       MAX-ACCESS not-accessible
       STATUS     current
       DESCRIPTION
             "Table defines number of Session Manager"
       ::= { remoteSessionManagerMIBObjects 2 }

remoteSessionManagerEntry OBJECT-TYPE
       	SYNTAX     RemoteSessionManagerEntry
		MAX-ACCESS not-accessible
       	STATUS     current
       	DESCRIPTION
             "Entry represents the AAA Server"
       	INDEX {	clientIndex }
       	::= { remoteSessionManagerStatTable 1 }

RemoteSessionManagerEntry ::= SEQUENCE {

	clientIndex						Integer32,
	remoteSMName					SnmpAdminString,
	remoteSMIPAddress				IpAddress,
	remoteSMRequestRx						Counter32,
	remoteSMResponsesTx					Counter32,
	remoteSMRequestDropped				Counter32,
	remoteSMUnknownRequestType			Counter32,
	remoteSMTimeoutRequest				Counter32,
	remoteSMAccessRequestRx				Counter32,
	remoteSMAccessAcceptTx				Counter32,
	remoteSMAccessRejectTx				Counter32,
	remoteSMAcctRequestRx					Counter32,
	remoteSMAcctStartRequestRx			Counter32,
	remoteSMAcctUpdateRequestRx			Counter32,
	remoteSMAcctStopRequestRx				Counter32,
	remoteSMAcctResponseTx	  			Counter32
}

clientIndex OBJECT-TYPE
       SYNTAX     Integer32
       MAX-ACCESS not-accessible
       STATUS     current
       DESCRIPTION
             ""
       ::= { remoteSessionManagerEntry 1 }

remoteSMName OBJECT-TYPE
       SYNTAX	SnmpAdminString
       MAX-ACCESS read-only
       STATUS     current
       DESCRIPTION
             "indicate the name of Remote Session Manager"
       ::= { remoteSessionManagerEntry 2 }
       
remoteSMIPAddress	OBJECT-TYPE
       SYNTAX     IpAddress
       MAX-ACCESS read-only
       STATUS     current
       DESCRIPTION
             "IP Address of configured Radius clients"
       ::= { remoteSessionManagerEntry 3}

remoteSMRequestRx OBJECT-TYPE
       SYNTAX     Counter32
       MAX-ACCESS read-only
       STATUS     current
       DESCRIPTION
             "Total No. of request received by Remote Session Manager"
       ::= { remoteSessionManagerEntry 4 }

remoteSMResponsesTx OBJECT-TYPE
       SYNTAX     Counter32
       MAX-ACCESS read-only
       STATUS     current
       DESCRIPTION
             "Total No. of response given by Remote Session Manager"
       ::= { remoteSessionManagerEntry 5 }

remoteSMRequestDropped OBJECT-TYPE
       SYNTAX     Counter32
       MAX-ACCESS read-only
       STATUS     current
       DESCRIPTION
             "Total No. of request dropped by Remote Session Manager"
       ::= { remoteSessionManagerEntry 6 }

remoteSMUnknownRequestType OBJECT-TYPE
       SYNTAX     Counter32
       MAX-ACCESS read-only
       STATUS     current
       DESCRIPTION
             "Total No. of unknown request received by Remote Session Manager"
       ::= { remoteSessionManagerEntry 7 }

remoteSMTimeoutRequest OBJECT-TYPE
       SYNTAX     Counter32
       MAX-ACCESS read-only
       STATUS     current
       DESCRIPTION
             "Total No. of unknown request received by Remote Session Manager"
       ::= { remoteSessionManagerEntry 8 }
       
remoteSMAccessRequestRx OBJECT-TYPE
       SYNTAX     Counter32
       MAX-ACCESS read-only
       STATUS     current
       DESCRIPTION
             "Total No. of access request received by Remote Session Manager"
       ::= { remoteSessionManagerEntry 9 }

remoteSMAccessAcceptTx OBJECT-TYPE
       SYNTAX     Counter32
       MAX-ACCESS read-only
       STATUS     current
       DESCRIPTION
             "Total No. of access accept given by Remote Session Manager"
       ::= { remoteSessionManagerEntry 10 }

remoteSMAccessRejectTx OBJECT-TYPE
       SYNTAX     Counter32
       MAX-ACCESS read-only
       STATUS     current
       DESCRIPTION
             "Total No. of access reject given by Remote Session Manager"
       ::= { remoteSessionManagerEntry 11 }

remoteSMAcctRequestRx OBJECT-TYPE
       SYNTAX     Counter32
       MAX-ACCESS read-only
       STATUS     current
       DESCRIPTION
             "Total No. of accounting request received by Remote Session Manager"
       ::= { remoteSessionManagerEntry 12 }

remoteSMAcctResponseTx OBJECT-TYPE
       SYNTAX     Counter32
       MAX-ACCESS read-only
       STATUS     current
       DESCRIPTION
             "Total No. of accounting response gived by Remote Session Manager"
       ::= { remoteSessionManagerEntry 13 }
       
remoteSMAcctStartRequestRx OBJECT-TYPE
       SYNTAX     Counter32
       MAX-ACCESS read-only
       STATUS     current
       DESCRIPTION
             "Total No. of accounting start received by Remote Session Manager"
       ::= { remoteSessionManagerEntry 14 }

remoteSMAcctUpdateRequestRx OBJECT-TYPE
       SYNTAX     Counter32
       MAX-ACCESS read-only
       STATUS     current
       DESCRIPTION
             "Total No. of accounting update received by Remote Session Manager"
       ::= { remoteSessionManagerEntry 15 }
 
remoteSMAcctStopRequestRx OBJECT-TYPE
       SYNTAX     Counter32
       MAX-ACCESS read-only
       STATUS     current
       DESCRIPTION
             "Total No. of accounting stop received by Remote Session Manager"
       ::= { remoteSessionManagerEntry 16 }

END
